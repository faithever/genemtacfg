CL-PKTC-EUE-RST-MIB DEFINITIONS ::= BEGIN
 
IMPORTS 
    MODULE-IDENTITY, 
    OBJECT-TYPE, 
    Unsigned32,
    Integer32 
                       FROM SNMPv2-SMI 
    OBJECT-GROUP, 
    MODULE-COMPLIANCE 
                       FROM SNMPv2-CONF 
    SnmpAdminString 
                       FROM SNMP-FRAMEWORK-MIB 
     
    TEXTUAL-CONVENTION, 
    TruthValue,
    RowStatus 
                       FROM SNMPv2-TC
    Uri
                       FROM URI-TC-MIB
    pktcApplicationMibs
                       FROM CLAB-DEF-MIB
    PktcEUETCAdminStatus,
    PktcEUETCOperStatus,
    PktcEUETCStatusInfo,
    PktcEUETCUsrAppIndexType
                       FROM CL-PKTC-EUE-TC-MIB
    pktcEUEDevOpIndex
                       FROM CL-PKTC-EUE-DEV-MIB;
                  
      
pktcEUERSTMIB MODULE-IDENTITY 
    LAST-UPDATED "201210300000Z" -- October 30, 2012 
    ORGANIZATION "Cable Television Laboratories, Inc." 
    CONTACT-INFO 
            "Broadband Network Services
             Cable Television Laboratories, Inc.
             858 Coal Creek Circle,
             Louisville, CO 80027, USA 
             Phone: +1 303-661-9100
             Email: mibs@cablelabs.com
        
             Acknowledgements:
             Thomas Clack, Broadcom - Primary author
             Satish Kumar, Texas Instruments,
             Eugene Nechamkin, Broadcom
             Sumanth Channabasappa, CableLabs
             John Berg, CableLabs
             Eduardo Cardona, CableLabs
             and members of the PacketCable 2.0 Provisioning Focus Team."
     DESCRIPTION 
            "This MIB module contains configuration MIB  
             objects for supporting RST Features specified in
             the PacketCable RST specification." 
    REVISION "201210300000Z"  
    DESCRIPTION
            "Revised Version includes ECN RST-EUE-PROV-N-12.0687-1
             and published as part of RST-EUE-PROV-I08-121030" 
    REVISION "201204120000Z" -- April 12, 2012 
    DESCRIPTION
            "Revised Version includes ECN RST-EUE-PROV-N-12.0675-2 
             and published as part of RST-EUE-PROV-I07-120412" 
    REVISION "201101040000Z" -- Jan 4, 2011
    DESCRIPTION
            "Revised Version includes ECN RST-EUE-PROV-N-10.0653-4
             and published as part of RST-EUE-PROV-I06-110127"
    REVISION "201004260000Z" -- April 26, 2010
    DESCRIPTION
            "Revised Version includes ECN RST-EUE-PROV-N-10.0630-3
             and published as part of RST-EUE-PROV-I05-100527" 
    REVISION "200912140000Z" -- December 14, 2009
    DESCRIPTION
            "Revised Version includes ECN RST-EUE-PROV-N-09.0608-4
             and published as part of RST-EUE-PROV-I04-100120" 
    REVISION "200905280000Z" -- May 28, 2009
    DESCRIPTION
            "Revised Version includes ECNs
             RST-EUE-PROV-N-08.0529-5
             RST-EUE-PROV-N-09.0558-3
            and published as part of RST-EUE-PROV-I03-090528" 
     REVISION "200807100000Z" -- July 10, 2008
     DESCRIPTION              
             "Revised Version includes ECN RST-EUE-PROV-N-08.0525-5
             and published as PKT-SP-RST-EUE-PROV-I02-080710"
     REVISION "200711060000Z" -- Nov 6, 2007
     DESCRIPTION
             "Initial version, published as part of the CableLabs
             RST E-UE Provisioning Specification
             PKT-SP-RST-EUE-PROV-I01-071106
             Copyright 2007 Cable Television Laboratories, Inc.
             All rights reserved."   
             
    
    ::= { pktcApplicationMibs 2 }

-- Administrative assignments    
pktcEUERSTNotifications     OBJECT IDENTIFIER ::= { pktcEUERSTMIB 0 }    
pktcEUERSTObjects           OBJECT IDENTIFIER ::= { pktcEUERSTMIB 1 }  
pktcEUERSTConformance       OBJECT IDENTIFIER ::= { pktcEUERSTMIB 2 }  
 
pktcEUERSTCompliances       OBJECT IDENTIFIER ::= { pktcEUERSTConformance 1 }  
pktcEUERSTGroups            OBJECT IDENTIFIER ::= { pktcEUERSTConformance 2 }  
 
-- MIB Objects 
pktcEUERSTProfile           OBJECT IDENTIFIER ::= { pktcEUERSTObjects 1 }  
pktcEUERSTFeatures          OBJECT IDENTIFIER ::= { pktcEUERSTObjects 2 }  
  
 
    
    
-- ---------------------------------------------------------------------           
-- Pktc EUE RST Textual Conventions 
-- ---------------------------------------------------------------------                     

PktcRSTTCFeatID ::= TEXTUAL-CONVENTION 
             STATUS  current 
             DESCRIPTION 
                 "This TEXTUAL CONVENTION is being defined 
                  as a way to enumerate the RST features." 
             SYNTAX   INTEGER { 
                               other(1),
                               digitMap(2),
                               basicCall(3), 
                               announcement(4),
                               statusChange(5),
                               noAnsTimeout(6),
                               callerId(7),
                               callerIdDisplay(8),
                               callerIdBlocking(9),
                               callerIdDelivery(10),
                               cfv(11),
                               callWaiting(12),
                               callHold(13),
                               callTransfer(14),
                               threeWayCalling(15),
                               doNotDisturb(16),
                               subscrProgPin(17),  -- Subscriber Programmable PIN
                               msgWaitIndicator(18),
                               autoRecall(19),
                               autoCallback(20),
                               busyLineVerify(21),
                               emergencySvc(22),
                               scf(23),            -- Selective Call Forwarding
                               acr(24),            -- Anonymous Call Rejection
                               solicitorBlocking(25),
                               distinctAlerting(26),
                               speedDialing(27),
                               cot(28),             -- Customer Originated Call Trace
                               heldMedia(29),
                               localSpeedDialing(30),
                               hotline(31),
                               digitMapVariable(32)
                               -- Reserved Range for operators specific features
                               -- identifiers 100 to 200
                               }                          

PktcEUETCRSTAppFeatIndexType ::= TEXTUAL-CONVENTION
    STATUS  current
    DESCRIPTION
          " This TEXTUAL CONVENTION is being defined to 
            indicate any indices related to RST Application
            Features.
            Such an instance can be referenced across
            tables to indicate an association."          
      SYNTAX   Unsigned32 (0..63)  
                  
 PktcEUETCRSTAUID ::= TEXTUAL-CONVENTION
      DISPLAY-HINT "255a"
      STATUS  current
      DESCRIPTION
          " This TEXTUAL CONVENTION is defined to 
            indicate the Application Unique Identifier (AUID)
            as defined by PacketCable.
            The AUID is used for the dynamic invocation of RST 
            features."
     SYNTAX      OCTET STRING
     
-- ---------------------------------------------------------------------                    
--  EUE Profile Information
-- ---------------------------------------------------------------------                    
pktcEUERSTProfileVersion OBJECT-TYPE
    SYNTAX      SnmpAdminString(SIZE(0..6))
    MAX-ACCESS  read-only
    STATUS      current
    DESCRIPTION
        " This MIB Object represents the RST Profile Version for this
          MIB module. The EUE MUST set this MIB Object to a value of '1.0'."
    ::= { pktcEUERSTProfile 1 }

-- ---------------------------------------------------------------------    
-- The Application Profile to Features Map Table
--  
-- ---------------------------------------------------------------------    
pktcEUERSTAppProfileToFeatTable OBJECT-TYPE
    SYNTAX      SEQUENCE OF PktcEUERSTAppProfileToFeatEntry
    MAX-ACCESS  not-accessible
    STATUS      current
    DESCRIPTION
        " This table specifies RST profiles that can be associated
          with Users supporting the RST application."
    ::= { pktcEUERSTProfile 2 } 
    
pktcEUERSTAppProfileToFeatEntry OBJECT-TYPE
    SYNTAX      PktcEUERSTAppProfileToFeatEntry
    MAX-ACCESS  not-accessible
    STATUS      current
    DESCRIPTION
        "Each entry in this table specifies an RST profile associated
         with a set of RST features. Each entry in this table is stored
         in volatile memory."
    INDEX  { pktcEUERSTAppProfileIndex, pktcEUERSTAppFeatIndex }
    ::= { pktcEUERSTAppProfileToFeatTable 1 } 
    
PktcEUERSTAppProfileToFeatEntry ::=
    SEQUENCE {                                
              pktcEUERSTAppProfileIndex       PktcEUETCUsrAppIndexType, 
              pktcEUERSTAppFeatIndex          PktcEUETCRSTAppFeatIndexType,
              pktcEUERSTAppFeatID             PktcRSTTCFeatID,
              pktcEUERSTAppFeatIndexRef       PktcEUETCRSTAppFeatIndexType,
              pktcEUERSTAppAdminStat          PktcEUETCAdminStatus,
              pktcEUERSTAppAdminStatInfo      PktcEUETCStatusInfo,
              pktcEUERSTAppOperStat           PktcEUETCOperStatus,
              pktcEUERSTAppOperStatInfo       PktcEUETCStatusInfo,
              pktcEUERSTAppStatus             RowStatus
             }

pktcEUERSTAppProfileIndex  OBJECT-TYPE
    SYNTAX      PktcEUETCUsrAppIndexType
    MAX-ACCESS  not-accessible
    STATUS      current
    DESCRIPTION
        " This MIB Object identifies an instance of an 
          RST application profile."
    ::= { pktcEUERSTAppProfileToFeatEntry 1 }

pktcEUERSTAppFeatIndex  OBJECT-TYPE
    SYNTAX      PktcEUETCRSTAppFeatIndexType
    MAX-ACCESS  not-accessible
    STATUS      current
    DESCRIPTION
        " This MIB Object identifies a specific RST feature
          instance."
    ::= { pktcEUERSTAppProfileToFeatEntry 2 }  
    
pktcEUERSTAppFeatID  OBJECT-TYPE
    SYNTAX      PktcRSTTCFeatID
    MAX-ACCESS  read-create
    STATUS      current
    DESCRIPTION
        " The MIB Object identifies a specific RST
          feature, as specified by PacketCable RST."
    ::= { pktcEUERSTAppProfileToFeatEntry 3 } 

pktcEUERSTAppFeatIndexRef  OBJECT-TYPE
    SYNTAX      PktcEUETCRSTAppFeatIndexType
    MAX-ACCESS  read-create
    STATUS      current
    DESCRIPTION
        " The MIB Object identifies an index into the RST
          feature table identified by the MIB Object
          pktcEUERSTAppFeatID.
          
          A value of '0' is reserved and is used to either
          identify a global feature configuration, or when
          no configuration data is specified for the feature.
          
          For example, the value of this object MUST be set to 
          '0' for a feature that has no associated additional 
          configuration table.
           
          Setting the value to '0' in any other cases will
          result in feature configuration error."
    ::= { pktcEUERSTAppProfileToFeatEntry 4 } 

pktcEUERSTAppAdminStat  OBJECT-TYPE
    SYNTAX      PktcEUETCAdminStatus
    MAX-ACCESS  read-create
    STATUS      current
    DESCRIPTION
        " This MIB Object contains the administratively desired
          activation status of the feature within the profile.

          When set to 'active' the feature is intended
          to be available to the applications that reference this 
          profile.

          When set to 'inactive' the feature is not available to the
          applications that reference this profile."           
    DEFVAL      {active}
    ::= { pktcEUERSTAppProfileToFeatEntry 5 }   

pktcEUERSTAppAdminStatInfo  OBJECT-TYPE
    SYNTAX      PktcEUETCStatusInfo
    MAX-ACCESS  read-create
    STATUS      current
    DESCRIPTION
        " This MIB Object MAY provide more information about the
          status reported by the MIB Object pktcEUERSTAppAdminStat."
    DEFVAL      {""}
    ::= { pktcEUERSTAppProfileToFeatEntry 6 } 

pktcEUERSTAppOperStat  OBJECT-TYPE
    SYNTAX      PktcEUETCOperStatus
    MAX-ACCESS  read-only
    STATUS      current
    DESCRIPTION
        " This MIB Object contains the operational activation status
          of a feature within a profile.
 
          This object returns the following values:
          
          'active' 
          When pktcEUERSTAppAdminStat is 'active' and there are 
          no run-time conditions and/or configuration errors that 
          prohibit the feature from being used. 
 
          'inactive' 
          When pktcEUERSTAppAdminStat is 'inactive' 
          or
          When pktcEUERSTAppAdminStat is 'active' and there 
          are run-time conditions and/or configuration errors 
          that prohibit the feature from being used. 
          
          'notPresent'
          When the application feature is not available or unknown
          to the EUE. 
          
          'unknown' 
          Other conditions not covered by the previous values.
          
          An example of a run-time condition that can result in a value
          of 'inactive' is an unsuccessful attempt to bind the resources 
          associated with the feature by an application because the 
          resources are currently bound to another profile.
 
          PacketCable applications can specify additional conditions for 
          how an application is considered 'active', 'inactive' or 
          'notPresent', and corresponding state machine."        
    ::= { pktcEUERSTAppProfileToFeatEntry 7 }   

pktcEUERSTAppOperStatInfo  OBJECT-TYPE
    SYNTAX      PktcEUETCStatusInfo
    MAX-ACCESS  read-only
    STATUS      current
    DESCRIPTION
        " This MIB Object MAY provide more information about the
          status reported by the MIB Object pktcEUERSTAppOperStat."
    DEFVAL      {""}
    ::= { pktcEUERSTAppProfileToFeatEntry 8 }
    
pktcEUERSTAppStatus  OBJECT-TYPE
    SYNTAX      RowStatus
    MAX-ACCESS  read-create
    STATUS      current
    DESCRIPTION
        " This MIB Object defines the row status associated with this
          particular application profile in the MIB table.

          An entry in this table is not qualified for activation
          until the object instances of all corresponding columns
          have been initialized, either by default values or via
          explicit SET operations.  Until all object instances in
          this row are initialized, the status value for this realm
          must be 'notReady(3)'.

          In particular, two columnar objects must be SET: the
          'pktcEUERSTAppFeatID' and 'pktcEUERSTAppFeatIndexRef'. 
          Once these two objects have been set the row status may be SET 
          to 'active(1)'.

          The EUE MUST not allow these two objects to be changed while
          the row is 'active'. The value of this object has no effect on
          whether other columnar objects in this row can be modified."
    ::= { pktcEUERSTAppProfileToFeatEntry 9 }  

                             
-- ---------------------------------------------------------------------                     
-- The Digit Map
-- Ref (PacketCable RST specification): 
-- ---------------------------------------------------------------------                     
pktcEUERSTDigitMapFeat  OBJECT IDENTIFIER ::= { pktcEUERSTProfile 3 }

-- ------------------------------------------
-- Digit Map Profile Table
-- ------------------------------------------
pktcEUERSTDigitMapProfileTable OBJECT-TYPE
    SYNTAX      SEQUENCE OF PktcEUERSTDigitMapProfileEntry
    MAX-ACCESS  not-accessible
    STATUS      current
    DESCRIPTION
        " This table provides a Digit Map Profile. A Digit Map
          Profile may be shared by multiple Users"
    ::= { pktcEUERSTDigitMapFeat 1 } 
    
pktcEUERSTDigitMapProfileEntry OBJECT-TYPE
    SYNTAX      PktcEUERSTDigitMapProfileEntry
    MAX-ACCESS  not-accessible
    STATUS      current
    DESCRIPTION
        "Each entry in this table provides a digit map profile."
    INDEX  { pktcEUERSTDMIndex }
    ::= { pktcEUERSTDigitMapProfileTable 1 } 
    
PktcEUERSTDigitMapProfileEntry ::=
    SEQUENCE {
              pktcEUERSTDMIndex           PktcEUETCRSTAppFeatIndexType,
              pktcEUERSTDMValue           OCTET STRING,
              pktcEUERSTDMStatus          RowStatus
             }

pktcEUERSTDMIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTDigitMapProfileEntry 1 }

pktcEUERSTDMValue  OBJECT-TYPE
    SYNTAX      OCTET STRING(SIZE(0..8192))
    MAX-ACCESS  read-create
    STATUS      current
    DESCRIPTION
        "This MIB Object specifies the ABNF for the Digit Map.
         Refer to the PacketCable RST Feature Specification 
         for representation and validation details."
   REFERENCE "PacketCable RST Feature Specification"
    ::= { pktcEUERSTDigitMapProfileEntry 2 }

pktcEUERSTDMStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTDigitMapProfileEntry 3 } 
             

-- ------------------------------------------
-- Digit Map Variable Table
-- ------------------------------------------
pktcEUERSTDigitMapVariableTable OBJECT-TYPE
    SYNTAX      SEQUENCE OF PktcEUERSTDigitMapVariableEntry
    MAX-ACCESS  not-accessible
    STATUS      current
    DESCRIPTION
        " This object represents Digit map extension variables 
        associated with a particular user application profile."
    ::= { pktcEUERSTDigitMapFeat 2 } 
    
pktcEUERSTDigitMapVariableEntry OBJECT-TYPE
    SYNTAX      PktcEUERSTDigitMapVariableEntry
    MAX-ACCESS  not-accessible
    STATUS      current
    DESCRIPTION
        "The conceptual row of pktcEUERSTDigitMapVariableTable."
    INDEX  { pktcEUERSTDigitMapVariableIndex, pktcEUERSTDigitMapVariableId }
    ::= { pktcEUERSTDigitMapVariableTable 1 } 
    
PktcEUERSTDigitMapVariableEntry ::=
    SEQUENCE {
              pktcEUERSTDigitMapVariableIndex        PktcEUETCRSTAppFeatIndexType,
              pktcEUERSTDigitMapVariableId           Unsigned32,
              pktcEUERSTDigitMapVariableName         SnmpAdminString,
              pktcEUERSTDigitMapVariableValue        SnmpAdminString,
              pktcEUERSTDigitMapVariableStatus       RowStatus
             }

pktcEUERSTDigitMapVariableIndex  OBJECT-TYPE
    SYNTAX      PktcEUETCRSTAppFeatIndexType
    MAX-ACCESS  not-accessible
    STATUS      current
    DESCRIPTION
        " This key represents the identifier of a Digit 
          Map Variable Feature List. Values used for this
          index must be greater than zero and are not required
          to be sequential."
    ::= { pktcEUERSTDigitMapVariableEntry 1 }

pktcEUERSTDigitMapVariableId  OBJECT-TYPE
    SYNTAX      Unsigned32
    MAX-ACCESS  not-accessible
    STATUS      current
    DESCRIPTION
        " This attribute represent the unique identifier of an instance 
          within the scope of a Digit Map Variable list."
    ::= { pktcEUERSTDigitMapVariableEntry 2 }

pktcEUERSTDigitMapVariableName  OBJECT-TYPE
    SYNTAX      SnmpAdminString
    MAX-ACCESS  read-create
    STATUS      current
    DESCRIPTION
        "This attribute represents the name of the Digit Map variable 
          being defined. More specifically, it represents the 
          'SymbolNameDef' part of the SymbolDef construct this 
          variable is referring."
   REFERENCE "PacketCable RST Feature Specification"
    ::= { pktcEUERSTDigitMapVariableEntry 3 }


pktcEUERSTDigitMapVariableValue  OBJECT-TYPE
    SYNTAX      SnmpAdminString
    MAX-ACCESS  read-create
    STATUS      current
    DESCRIPTION
        "This attribute represents the value of the  Digit Map 
        variable being defined. See Notation and rules in the RST 
        Feature specification."
   REFERENCE "PacketCable RST Feature Specification"
    ::= { pktcEUERSTDigitMapVariableEntry 4 }

pktcEUERSTDigitMapVariableStatus  OBJECT-TYPE 
    SYNTAX      RowStatus 
    MAX-ACCESS  read-create 
    STATUS      current 
    DESCRIPTION 
          "There is no restriction on the ability to change values in 
          this instance while is active.
          A created instance can be set to active only after all 
          corresponding attributes of the object instances have been
          set to valid values." 
    ::= { pktcEUERSTDigitMapVariableEntry 5 } 

-- ---------------------------------------------------------------------                     
-- The In-service/Out-of-Service 
-- Ref (PacketCable RST specification): 
-- ---------------------------------------------------------------------                     
pktcEUERSTKeepAlive OBJECT-TYPE
    SYNTAX      TruthValue
    MAX-ACCESS  read-write
    STATUS      deprecated
    DESCRIPTION
        " This MIB Object represents the configuration of the in-service/
          out-of-service status.
          The value 'true' indicates the EUE use the keep-alive mechanism
          to determine the in-service/out-of-service status. The value 'false'
          indicates the EUE follows the in-service state requirement of RSTF.
          This MIB object is deprecated in favor of pktcEUERSTKeepAliveSetting."
    REFERENCE "PacketCable RST Feature Specification"
    ::= { pktcEUERSTProfile 4 }

pktcEUERSTKeepAliveSetting OBJECT-TYPE
    SYNTAX      INTEGER {
                  on(1),
                  off(2),
                  conditional(3)
                }
    MAX-ACCESS  read-write
    STATUS      current
    DESCRIPTION
        " This MIB Object represents the configuration of the in-service/
          out-of-service status.
          The value 'on' indicates the EUE use the keep-alive mechanism
          to determine the in-service/out-of-service status. The value 'off'
          indicates the EUE follows the in-service state requirement of RSTF.
          The value 'conditional' indicates the EUE MUST either start the  
          keep alivemechanism (as described above) or not depending on the 
          indication (or lack thereof) in the 200 OK response to the REGISTER. "
    REFERENCE "PacketCable RST Feature Specification"
    ::= { pktcEUERSTProfile 5 }


-- ---------------------------------------------------------------------                     
-- The Basic Call Features 
-- Ref (PacketCable RST specification): Table "Basic Call Feature Data" 
-- ---------------------------------------------------------------------                     
pktcEUERSTBasicCallFeat  OBJECT IDENTIFIER ::= { pktcEUERSTFeatures 1 } 
 
-- The USER Basic-Call Feature Table

pktcEUERSTBasicCallTable OBJECT-TYPE
    SYNTAX      SEQUENCE OF PktcEUERSTBasicCallEntry
    MAX-ACCESS  not-accessible
    STATUS      current
    DESCRIPTION
        " This data table represents User-based parameters
          associated with the Basic Call Feature for the 
          RST Service."
    ::= { pktcEUERSTBasicCallFeat 1 } 
    
pktcEUERSTBasicCallEntry OBJECT-TYPE
    SYNTAX      PktcEUERSTBasicCallEntry
    MAX-ACCESS  not-accessible
    STATUS      current
    DESCRIPTION
        " Each entry in this data table describes an association
          of a user with a Basic Call Feature parameter.
          Each entry in this table is stored in volatile memory."
    INDEX  { pktcEUERSTBCallIndex }
    ::= { pktcEUERSTBasicCallTable 1 } 
    
PktcEUERSTBasicCallEntry ::=
    SEQUENCE {
              pktcEUERSTBCallIndex    PktcEUETCRSTAppFeatIndexType,
              pktcEUERSTBCallPrefCodecList
                                      SnmpAdminString,
              pktcEUERSTBCallStatus   RowStatus
             }

pktcEUERSTBCallIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTBasicCallEntry 1 }
   
pktcEUERSTBCallPrefCodecList  OBJECT-TYPE 
    SYNTAX      SnmpAdminString 
    MAX-ACCESS  read-create 
    STATUS      current 
    DESCRIPTION 
        " This MIB Object contains the list of the voice and/or video
          codecs preferred by the network.        
          The value in this object is formed as a comma-separated list 
          of the well-known literal voice/video codec names in order
          of preference from left to right. The EUE MUST use the literal
          voice and/or video codec name as per RTP AV Profile 
          [RFC 3551], or per encoding names registered with the IANA, 
          or per encoding names referenced or defined in the PacketCable
          Codec-Media specification.
          Unknown or non-supported codecs are ignored.
          The zero-length string indicates the preferred codec list is 
          vendor specific starting with G711 codecs."
    REFERENCE "PacketCable Residential SIP Telephony Feature Specification" 
    ::= { pktcEUERSTBasicCallEntry 2 }
    
pktcEUERSTBCallStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTBasicCallEntry 3 }      


-- ---------------------------------------------------------------------                     
-- The NETWORK Basic-Call Feature Table
-- Ref (PacketCable RST specification): Table "Basic Call Feature Data" 
-- ---------------------------------------------------------------------                     

pktcEUERSTNfBasicCallTable OBJECT-TYPE
    SYNTAX      SEQUENCE OF PktcEUERSTNfBasicCallEntry
    MAX-ACCESS  not-accessible
    STATUS      current
    DESCRIPTION
        " This data table represents Network-based parameters
          associated with the Basic Call Feature for the 
          RST Service."
    ::= { pktcEUERSTBasicCallFeat 2 } 
    
pktcEUERSTNfBasicCallEntry OBJECT-TYPE
    SYNTAX      PktcEUERSTNfBasicCallEntry
    MAX-ACCESS  not-accessible
    STATUS      current
    DESCRIPTION
        " Each entry in this data table describes an association
          of an Network Service Provider with a Basic Call Feature
          parameter."
    INDEX  { pktcEUEDevOpIndex }
    ::= { pktcEUERSTNfBasicCallTable 1 } 
    
PktcEUERSTNfBasicCallEntry ::=
    SEQUENCE {
              pktcEUERSTNfBCallByeDelay            Unsigned32,
              pktcEUERSTNfBCallOrigDTTimer         Unsigned32,
              pktcEUERSTNfBCallTermOHErrSig        Uri,
              pktcEUERSTNfBCallTermErrSigTimer     Unsigned32,   
              pktcEUERSTNfBCallPermSeqTone1        Uri,
              pktcEUERSTNfBCallPermSeqTimer1       Unsigned32,
              pktcEUERSTNfBCallPermSeqTone2        Uri,
              pktcEUERSTNfBCallPermSeqTimer2       Unsigned32,
              pktcEUERSTNfBCallPermSeqTone3        Uri,
              pktcEUERSTNfBCallPermSeqTimer3       Unsigned32,
              pktcEUERSTNfBCallLORTimer            Unsigned32,
              pktcEUERSTNfBCallNEMDSCPValueMedia   Unsigned32,
              pktcEUERSTNfBCallNEMDSCPValueSig     Unsigned32,
              pktcEUERSTNfBCallStatus              RowStatus,
              pktcEUERSTNFBCallOrigModLongIntDig   Unsigned32,
              pktcEUERSTNfBCallPermSeqTone4        Uri,
              pktcEUERSTNfBCallPermSeqTimer4       Unsigned32,
              pktcEUERSTNfBCallOverrideNotifyRejected TruthValue
             }
          
pktcEUERSTNfBCallByeDelay  OBJECT-TYPE 
    SYNTAX      Unsigned32 
    MAX-ACCESS  read-create 
    STATUS      current 
    DESCRIPTION 
        " This MIB Object specifies the Bye Delay in seconds." 
    REFERENCE "PacketCable Residential SIP Telephony Feature Specification" 
    ::= { pktcEUERSTNfBasicCallEntry 1 }  

pktcEUERSTNfBCallOrigDTTimer  OBJECT-TYPE 
    SYNTAX      Unsigned32 
    MAX-ACCESS  read-create 
    STATUS      current 
    DESCRIPTION 
        " This MIB Object specifies the Origination Mode 
          Dial Tone Timer in seconds." 
    REFERENCE "PacketCable Residential SIP Telephony Feature Specification" 
    ::= { pktcEUERSTNfBasicCallEntry 2 } 
 
pktcEUERSTNfBCallTermOHErrSig  OBJECT-TYPE 
    SYNTAX      Uri 
    MAX-ACCESS  read-create 
    STATUS      current 
    DESCRIPTION 
        " This MIB Object specifies the Termination Mode Off-Hook 
          error signal." 
    REFERENCE "PacketCable Residential SIP Telephony Feature Specification" 
    ::= { pktcEUERSTNfBasicCallEntry 3 } 
                                           
pktcEUERSTNfBCallTermErrSigTimer  OBJECT-TYPE 
    SYNTAX      Unsigned32 
    MAX-ACCESS  read-create 
    STATUS      current 
    DESCRIPTION 
        " This MIB Object specifies the Termination Mode error signal 
          timer in seconds." 
    REFERENCE "PacketCable Residential SIP Telephony Feature Specification" 
    ::= { pktcEUERSTNfBasicCallEntry 4 } 
     
pktcEUERSTNfBCallPermSeqTone1  OBJECT-TYPE 
    SYNTAX      Uri 
    MAX-ACCESS  read-create 
    STATUS      current 
    DESCRIPTION 
        " This MIB Object specifies the Permanent Sequence tone 1." 
    REFERENCE "PacketCable Residential SIP Telephony Feature Specification" 
    ::= { pktcEUERSTNfBasicCallEntry 5 } 
 
pktcEUERSTNfBCallPermSeqTimer1  OBJECT-TYPE 
    SYNTAX      Unsigned32 
    MAX-ACCESS  read-create 
    STATUS      current 
    DESCRIPTION 
        " This MIB Object specifies the Permanent Sequence timer 1
          in seconds." 
    REFERENCE "PacketCable Residential SIP Telephony Feature Specification" 
    ::= { pktcEUERSTNfBasicCallEntry 6 } 
  
pktcEUERSTNfBCallPermSeqTone2  OBJECT-TYPE 
    SYNTAX      Uri 
    MAX-ACCESS  read-create 
    STATUS      current 
    DESCRIPTION 
        " This MIB Object specifies the Permanent Sequence tone 2." 
    REFERENCE "PacketCable Residential SIP Telephony Feature Specification" 
    ::= { pktcEUERSTNfBasicCallEntry 7 } 
 
pktcEUERSTNfBCallPermSeqTimer2  OBJECT-TYPE 
    SYNTAX      Unsigned32 
    MAX-ACCESS  read-create 
    STATUS      current 
    DESCRIPTION 
        " This MIB Object specifies the Permanent Sequence timer 2
          in seconds." 
    REFERENCE "PacketCable Residential SIP Telephony Feature Specification" 
    ::= { pktcEUERSTNfBasicCallEntry 8 } 

pktcEUERSTNfBCallPermSeqTone3  OBJECT-TYPE 
     SYNTAX      Uri 
     MAX-ACCESS  read-create 
     STATUS      current 
     DESCRIPTION 
         " This MIB Object specifies the Permanent Sequence tone 3." 
     REFERENCE "PacketCable Residential SIP Telephony Feature Specification" 
     ::= { pktcEUERSTNfBasicCallEntry 9 } 
  
pktcEUERSTNfBCallPermSeqTimer3  OBJECT-TYPE 
     SYNTAX      Unsigned32 
     MAX-ACCESS  read-create 
     STATUS      current 
     DESCRIPTION 
         " This MIB Object specifies the Permanent Sequence timer 3
           in seconds." 
     REFERENCE "PacketCable Residential SIP Telephony Feature Specification" 
    ::= { pktcEUERSTNfBasicCallEntry 10 } 

pktcEUERSTNfBCallLORTimer  OBJECT-TYPE 
    SYNTAX      Unsigned32 
    MAX-ACCESS  read-create 
    STATUS      current 
    DESCRIPTION 
        " This MIB Object specifies the Lockout Reset timer in seconds." 
    REFERENCE "PacketCable Residential SIP Telephony Feature Specification" 
    ::= { pktcEUERSTNfBasicCallEntry 11 } 

pktcEUERSTNfBCallNEMDSCPValueMedia  OBJECT-TYPE 
    SYNTAX      Unsigned32(0..63) 
    MAX-ACCESS  read-create 
    STATUS      current 
    DESCRIPTION 
        " This MIB Object specifies the Non-Emergency DSCP Value
        for network packets carrying the Media (RTP) information." 
    REFERENCE "PacketCable Residential SIP Telephony Feature Specification" 
    ::= { pktcEUERSTNfBasicCallEntry 12 } 

pktcEUERSTNfBCallNEMDSCPValueSig  OBJECT-TYPE 
    SYNTAX      Unsigned32(0..63) 
    MAX-ACCESS  read-create 
    STATUS      current 
    DESCRIPTION 
        " This MIB Object specifies the Non-Emergency DSCP Value
        for network packets carrying the signaling information." 
    REFERENCE "PacketCable Residential SIP Telephony Feature Specification" 
    ::= { pktcEUERSTNfBasicCallEntry 13 } 
    
pktcEUERSTNfBCallStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNfBasicCallEntry 14 }  
   
pktcEUERSTNFBCallOrigModLongIntDig   OBJECT-TYPE 
    SYNTAX      Unsigned32 
    MAX-ACCESS  read-create 
    STATUS      current 
    DESCRIPTION 
        " This MIB Object specifies the Origination Mode Long Interdigit
          Timer in seconds." 
    REFERENCE "PacketCable Residential SIP Telephony Feature Specification" 
    ::= { pktcEUERSTNfBasicCallEntry 15 } 


pktcEUERSTNfBCallPermSeqTone4  OBJECT-TYPE 
     SYNTAX      Uri 
     MAX-ACCESS  read-create 
     STATUS      current 
     DESCRIPTION 
         " This MIB Object specifies the Permanent Sequence tone 4." 
     REFERENCE "PacketCable Residential SIP Telephony Feature Specification" 
     ::= { pktcEUERSTNfBasicCallEntry 16 } 
  
pktcEUERSTNfBCallPermSeqTimer4  OBJECT-TYPE 
     SYNTAX      Unsigned32 
     MAX-ACCESS  read-create 
     STATUS      current 
     DESCRIPTION 
         " This MIB Object specifies the Permanent Sequence timer 4
           in seconds." 
     REFERENCE "PacketCable Residential SIP Telephony Feature Specification" 
    ::= { pktcEUERSTNfBasicCallEntry 17 } 

pktcEUERSTNfBCallOverrideNotifyRejected  OBJECT-TYPE 
     SYNTAX      TruthValue 
     MAX-ACCESS  read-create 
     STATUS      current 
     DESCRIPTION 
         " This MIB Object specifies a control mechanism to override the
           NOTIFY Rejected Event behavior.

           The value 'true' instructs the UE to follow the behavior of 
           receiving a reg event NOTIFY with the associated event 
           attribute element  'deactivated' for the case where the 
           event attribute is set to 'rejected'. In other words, 
           if this attribute is set to 'true' the UE public identities 
           associated with this operator will e.g., de-register and start
           registration when the reg event attribute is set to 'rejected'. 

           The value 'false' indicates the UE follows the standard 
           procedures defined in the PacketCable IMS Delta Specification
            24.229 for the 'rejected' attribute of the reg event." 
     REFERENCE "PacketCable Residential SIP Telephony Feature Specification" 
     DEFVAL { false }
    ::= { pktcEUERSTNfBasicCallEntry 18 } 

-- ---------------------------------------------------------------------                     
-- Pktc EUE RST Announcement Feature Profile 
-- Ref (PacketCable RST specification): Table "Announcement Feature Data" 
-- ---------------------------------------------------------------------                     
pktcEUERSTAncFeat  OBJECT IDENTIFIER ::= { pktcEUERSTFeatures 2 } 
 
-- The USER Announcement Feature Table

pktcEUERSTAncTable OBJECT-TYPE
    SYNTAX      SEQUENCE OF PktcEUERSTAncEntry
    MAX-ACCESS  not-accessible
    STATUS      current
    DESCRIPTION
        " This data table represents User-based parameters
          associated with the Announcement Feature for the 
          RST Service."
    ::= { pktcEUERSTAncFeat 1 } 
    
pktcEUERSTAncEntry OBJECT-TYPE
    SYNTAX      PktcEUERSTAncEntry
    MAX-ACCESS  not-accessible
    STATUS      current
    DESCRIPTION
        " Each entry in this data table describes an association
          of a user with an Announcement Feature parameter.
          Each entry in this table is stored in volatile memory."
    INDEX  { pktcEUERSTAncIndex }
    ::= { pktcEUERSTAncTable 1 } 
    
PktcEUERSTAncEntry ::=
    SEQUENCE {
              pktcEUERSTAncIndex      PktcEUETCRSTAppFeatIndexType,
              pktcEUERSTAncPrefLang   SnmpAdminString,
              pktcEUERSTAncStatus     RowStatus
             } 
 
pktcEUERSTAncIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTAncEntry 1 }
 
pktcEUERSTAncPrefLang  OBJECT-TYPE 
    SYNTAX      SnmpAdminString 
    MAX-ACCESS  read-create 
    STATUS      current 
    DESCRIPTION 
        " This MIB Object specifies the preferred language for the 
          EUE announcement." 
    REFERENCE "PacketCable Residential SIP Telephony Feature Specification" 
    ::= { pktcEUERSTAncEntry 2 } 

pktcEUERSTAncStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTAncEntry 3 }  
   
-- ---------------------------------------------------------------------                     
-- The NETWORK Announcement Call Feature Table
-- Ref (PacketCable RST specification): Table "Announcement Feature Data" 
-- ---------------------------------------------------------------------                     

pktcEUERSTNfAncTable OBJECT-TYPE
    SYNTAX      SEQUENCE OF PktcEUERSTNfAncEntry
    MAX-ACCESS  not-accessible
    STATUS      current
    DESCRIPTION
        " This data table represents Network-based parameters
          associated with the Announcement Feature for the 
          RST Service."
    ::= { pktcEUERSTAncFeat 2 } 
    
pktcEUERSTNfAncEntry OBJECT-TYPE
    SYNTAX      PktcEUERSTNfAncEntry
    MAX-ACCESS  not-accessible
    STATUS      current
    DESCRIPTION
        " Each entry in this data table describes an association
          of an Network Service Provider with an Announcement Feature
          parameter. Each entry in this table is stored in volatile memory."
    INDEX  { pktcEUEDevOpIndex }
    ::= { pktcEUERSTNfAncTable 1 } 
    
PktcEUERSTNfAncEntry ::=
    SEQUENCE {
              pktcEUERSTNfAncRes                Uri,
              pktcEUERSTNfAncDomain             SnmpAdminString,
              pktcEUERSTNfAncPath               Uri,
              pktcEUERSTNfAncMIMEType           SnmpAdminString,
              pktcEUERSTNfAncStatus             RowStatus
             }
          
pktcEUERSTNfAncRes  OBJECT-TYPE 
    SYNTAX      Uri 
    MAX-ACCESS  read-create 
    STATUS      current 
    DESCRIPTION 
        " This MIB Object specifies the Announcement Resource 
          URI for the media server" 
    REFERENCE "PacketCable Residential SIP Telephony Feature Specification" 
    ::= { pktcEUERSTNfAncEntry 1 } 

pktcEUERSTNfAncDomain  OBJECT-TYPE 
    SYNTAX      SnmpAdminString 
    MAX-ACCESS  read-create 
    STATUS      current 
    DESCRIPTION 
        " This MIB Object specifies the Announcement Domain." 
    REFERENCE "PacketCable Residential SIP Telephony Feature Specification" 
    ::= { pktcEUERSTNfAncEntry 2 } 
 
pktcEUERSTNfAncPath  OBJECT-TYPE 
    SYNTAX      Uri 
    MAX-ACCESS  read-create 
    STATUS      current 
    DESCRIPTION 
        " This MIB Object specifies the Announcement Path." 
    REFERENCE "PacketCable Residential SIP Telephony Feature Specification" 
    ::= { pktcEUERSTNfAncEntry 3 } 
 
pktcEUERSTNfAncMIMEType OBJECT-TYPE 
    SYNTAX      SnmpAdminString 
    MAX-ACCESS  read-create 
    STATUS      current 
    DESCRIPTION 
        " This MIB Object specifies the Announcement MIME type." 
    REFERENCE "PacketCable Residential SIP Telephony Feature Specification" 
    ::= { pktcEUERSTNfAncEntry 4 } 

pktcEUERSTNfAncStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNfAncEntry 5 }  
    
-- ---------------------------------------------------------------------                     
-- The NETWORK Announcement Map Feature Table
-- Ref (PacketCable RST specification): Table "Announcement Feature Data" 
-- ---------------------------------------------------------------------                     

pktcEUERSTNfAncMapTable OBJECT-TYPE 
    SYNTAX      SEQUENCE OF PktcEUERSTNfAncMapEntry 
    MAX-ACCESS  not-accessible 
    STATUS      current 
    DESCRIPTION 
        " This data table represents the network-based announcement MAP entries" 
    REFERENCE "PacketCable Residential SIP Telephony Feature Specification" 
    ::= { pktcEUERSTAncFeat 3 }  
     
pktcEUERSTNfAncMapEntry OBJECT-TYPE 
    SYNTAX      PktcEUERSTNfAncMapEntry 
    MAX-ACCESS  not-accessible 
    STATUS      current 
    DESCRIPTION 
        " This data table represents the network-based announcement MAP entries. 
          Each entry in this table represents the Announcement MAP  
          entry URI corresponding to a response code. 
          Each entry in this table is stored in volatile memory." 
    REFERENCE "PacketCable Residential SIP Telephony Feature Specification" 
    INDEX  {pktcEUEDevOpIndex, pktcEUERSTNfAncMapRspCode} 
    ::= { pktcEUERSTNfAncMapTable 1 }  
     
PktcEUERSTNfAncMapEntry ::= 
    SEQUENCE { 
              pktcEUERSTNfAncMapRspCode        Unsigned32, 
              pktcEUERSTNfAncMapURI            Uri,
              pktcEUERSTNfAncMapStatus         RowStatus 
             } 
 
pktcEUERSTNfAncMapRspCode OBJECT-TYPE 
    SYNTAX      Unsigned32(400..603)
    MAX-ACCESS  not-accessible 
    STATUS      current 
    DESCRIPTION 
        " This MIB Object specifies the Response code. The following 
        Response codes are valid: 404, 406, 408, 480, 484, 500, 503, 
        504, 600, 603." 
    REFERENCE "PacketCable Residential SIP Telephony Feature Specification" 
    ::= { pktcEUERSTNfAncMapEntry 1 }   

pktcEUERSTNfAncMapURI OBJECT-TYPE 
    SYNTAX      Uri 
    MAX-ACCESS  read-create 
    STATUS      current 
    DESCRIPTION 
        " This MIB Object specifies the Announcement Map entry. 
          A string identifying the URI for response code." 
    REFERENCE "PacketCable Residential SIP Telephony Feature Specification" 
    ::= { pktcEUERSTNfAncMapEntry 2 } 
 
pktcEUERSTNfAncMapStatus OBJECT-TYPE 
    SYNTAX      RowStatus 
    MAX-ACCESS  read-create 
    STATUS      current 
    DESCRIPTION 
        " The status of this conceptual row. 
          There is no restriction on the ability to change values in this 
          row while the row is active.
          A created row can be set to active only after all corresponding
          instances of objects in the row have been set to valid values." 
    ::= { pktcEUERSTNfAncMapEntry 3 }  

-- ---------------------------------------------------------------------                     
-- The NETWORK Announcement Media Map Feature Table
-- Ref (PacketCable RST specification): Table "Announcement Feature Data" 
-- ---------------------------------------------------------------------                     
 
pktcEUERSTNfAncMediaMapTable OBJECT-TYPE 
    SYNTAX      SEQUENCE OF PktcEUERSTNfAncMediaMapEntry 
    MAX-ACCESS  not-accessible 
    STATUS      current 
    DESCRIPTION 
        " This data table represents the network-based announcement 
          Media MAP entries" 
    REFERENCE "PacketCable Residential SIP Telephony Feature Specification" 
    ::= { pktcEUERSTAncFeat 4 }  
     
pktcEUERSTNfAncMediaMapEntry OBJECT-TYPE 
    SYNTAX      PktcEUERSTNfAncMediaMapEntry 
    MAX-ACCESS  not-accessible 
    STATUS      current 
    DESCRIPTION 
        " This data table represents the announcement Media MAP entries. 
          Each entry in this table represents the Announcement Media MAP  
          entry URI corresponding to an announcement identifier.
          Each entry in this table is stored in volatile memory."
    REFERENCE "PacketCable Residential SIP Telephony Feature Specification" 
    INDEX  {pktcEUEDevOpIndex, pktcEUERSTNfAncMediaId} 
    ::= { pktcEUERSTNfAncMediaMapTable 1 }  
     
PktcEUERSTNfAncMediaMapEntry ::= 
    SEQUENCE { 
              pktcEUERSTNfAncMediaId             SnmpAdminString, 
              pktcEUERSTNfAncMediaURI            Uri,
              pktcEUERSTNfAncMediaCachMaxAge     Unsigned32, 
              pktcEUERSTNfAncMediaStatus         RowStatus
             }    
 
pktcEUERSTNfAncMediaId OBJECT-TYPE 
    SYNTAX      SnmpAdminString (SIZE (0..108)) 
    MAX-ACCESS  not-accessible 
    STATUS      current 
    DESCRIPTION 
        " This MIB Object specifies the announcement Identifier." 
    REFERENCE "PacketCable Residential SIP Telephony Feature Specification" 
    ::= { pktcEUERSTNfAncMediaMapEntry 1 }   
     
pktcEUERSTNfAncMediaURI OBJECT-TYPE 
    SYNTAX      Uri (SIZE (0..108))
    MAX-ACCESS  read-create 
    STATUS      current 
    DESCRIPTION 
        " This MIB Object specifies the Announcement Media Map entry. 
          A string identifying the URI for announcement identifier." 
    REFERENCE "PacketCable Residential SIP Telephony Feature Specification" 
    ::= { pktcEUERSTNfAncMediaMapEntry 2 } 

pktcEUERSTNfAncMediaCachMaxAge OBJECT-TYPE 
    SYNTAX      Unsigned32 
    MAX-ACCESS  read-create 
    STATUS      current 
    DESCRIPTION 
        " This MIB Object specifies the Announcement Media Cache 
          maximum age in seconds." 
    REFERENCE "PacketCable Residential SIP Telephony Feature Specification" 
    ::= { pktcEUERSTNfAncMediaMapEntry 3 } 

pktcEUERSTNfAncMediaStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNfAncMediaMapEntry 4 }
    
-- ---------------------------------------------------------------------                     
-- The NETWORK Announcement Local Media Feature Table            
-- Ref (PacketCable RST specification): Table "Local Media" 
-- ---------------------------------------------------------------------                     
                  
pktcEUERSTNfAncLocalMediaTable OBJECT-TYPE 
    SYNTAX      SEQUENCE OF PktcEUERSTNfAncLocalMediaEntry 
    MAX-ACCESS  not-accessible 
    STATUS      current 
    DESCRIPTION 
        " This data table represents the network-based Local Media entries" 
    REFERENCE "PacketCable Residential SIP Telephony Feature Specification" 
    ::= { pktcEUERSTAncFeat 5 }  
     
pktcEUERSTNfAncLocalMediaEntry OBJECT-TYPE 
    SYNTAX      PktcEUERSTNfAncLocalMediaEntry 
    MAX-ACCESS  not-accessible 
    STATUS      current 
    DESCRIPTION 
        " Each entry in this table represents the Local Media   
          entries. Each entry in this table is stored in volatile memory." 
    INDEX  {pktcEUEDevOpIndex, pktcEUERSTNfAncLclMediaURI} 
    ::= { pktcEUERSTNfAncLocalMediaTable 1 }  
     
PktcEUERSTNfAncLocalMediaEntry ::= 
    SEQUENCE { 
              pktcEUERSTNfAncLclMediaURI         Uri, 
              pktcEUERSTNfAncLclMediaType        SnmpAdminString, 
              pktcEUERSTNfAncLclMediaData        SnmpAdminString,
              pktcEUERSTNfAncLclMediaStatus      RowStatus 
             } 
             
pktcEUERSTNfAncLclMediaURI OBJECT-TYPE 
    SYNTAX      Uri (SIZE (0..108))
    MAX-ACCESS  not-accessible 
    STATUS      current 
    DESCRIPTION 
        " This MIB Object specifies the Local Media entry. 
          A string identifying the URI for the Local Media." 
    REFERENCE "PacketCable Residential SIP Telephony Feature Specification" 
    ::= { pktcEUERSTNfAncLocalMediaEntry 1 }   
     
pktcEUERSTNfAncLclMediaType OBJECT-TYPE 
    SYNTAX      SnmpAdminString 
    MAX-ACCESS  read-create 
    STATUS      current 
    DESCRIPTION 
        " This MIB Object specifies the Media Type entry." 
    REFERENCE "PacketCable Residential SIP Telephony Feature Specification" 
    ::= { pktcEUERSTNfAncLocalMediaEntry 2 } 
 
pktcEUERSTNfAncLclMediaData OBJECT-TYPE 
    SYNTAX      SnmpAdminString 
    MAX-ACCESS  read-create 
    STATUS      current 
    DESCRIPTION 
        " This MIB Object specifies the Media Data entry." 
    REFERENCE "PacketCable Residential SIP Telephony Feature Specification" 
    ::= { pktcEUERSTNfAncLocalMediaEntry 3 } 
 
pktcEUERSTNfAncLclMediaStatus OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNfAncLocalMediaEntry 4 }
 
-- ---------------------------------------------------------------------                     
-- Pktc EUE RST EUE ActStatus Change Feature Profile 
-- Ref (PacketCable RST specification): "UE ActStatus Change Feature Data" 
-- ---------------------------------------------------------------------                     
pktcEUERSTUEActStatChgFeat  OBJECT IDENTIFIER ::= { pktcEUERSTFeatures 3 } 
     
-- The USER EUE ActStatus Change Feature Table

pktcEUERSTUEActStatChgTable OBJECT-TYPE
    SYNTAX      SEQUENCE OF PktcEUERSTUEActStatChgEntry
    MAX-ACCESS  not-accessible
    STATUS      current
    DESCRIPTION
        " This data table represents User-based parameters
          associated with the EUE ActStatus Change Feature for the 
          RST Service."
    ::= { pktcEUERSTUEActStatChgFeat 1 } 
    
pktcEUERSTUEActStatChgEntry OBJECT-TYPE
    SYNTAX      PktcEUERSTUEActStatChgEntry
    MAX-ACCESS  not-accessible
    STATUS      current
    DESCRIPTION
        " Each entry in this data table describes an association
          of a user with a EUE ActStatus Change Feature parameter.
          Each entry in this table is stored in volatile memory."
    INDEX  { pktcEUERSTUEActStatChgIndex }
    ::= { pktcEUERSTUEActStatChgTable 1 } 
    
PktcEUERSTUEActStatChgEntry ::=
    SEQUENCE {
              pktcEUERSTUEActStatChgIndex    PktcEUETCRSTAppFeatIndexType,
              pktcEUERSTUEActStatChgRegExp   Unsigned32,
              pktcEUERSTUEActStatChgStatus   RowStatus
             }

pktcEUERSTUEActStatChgIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTUEActStatChgEntry 1 }
 
pktcEUERSTUEActStatChgRegExp  OBJECT-TYPE 
    SYNTAX      Unsigned32 
    MAX-ACCESS  read-create 
    STATUS      current 
    DESCRIPTION 
        " This MIB Object specifies the EUE ActStatus Registration expiration 
          in seconds." 
    REFERENCE "PacketCable Residential SIP Telephony Feature Specification" 
    ::= { pktcEUERSTUEActStatChgEntry 2 } 

pktcEUERSTUEActStatChgStatus OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTUEActStatChgEntry 3 }
      
-- ---------------------------------------------------------------------                     
-- Pktc EUE RST No Answer Timeout Feature Profile 
-- Ref (PacketCable RST specification): "No Answer Timeout Feature Data" 
-- ---------------------------------------------------------------------                     
pktcEUERSTNoAnsTimeoutFeat  OBJECT IDENTIFIER ::= { pktcEUERSTFeatures 4 } 
 
-- The USER No Answer timeout Feature Table

pktcEUERSTNoAnsTimeoutTable OBJECT-TYPE
    SYNTAX      SEQUENCE OF PktcEUERSTNoAnsTimeoutEntry
    MAX-ACCESS  not-accessible
    STATUS      current
    DESCRIPTION
        " This data table represents User-based parameters
          associated with the No Answer Timeout Feature for the 
          RST Service."
    ::= { pktcEUERSTNoAnsTimeoutFeat 1 } 
    
pktcEUERSTNoAnsTimeoutEntry OBJECT-TYPE
    SYNTAX      PktcEUERSTNoAnsTimeoutEntry
    MAX-ACCESS  not-accessible
    STATUS      current
    DESCRIPTION
        " Each entry in this data table describes an association
          of a user with a No Answer Timeout Feature parameter.
          Each entry in this table is stored in volatile memory."
    INDEX  { pktcEUERSTNoAnsTOIndex }
    ::= { pktcEUERSTNoAnsTimeoutTable 1 } 
    
PktcEUERSTNoAnsTimeoutEntry ::=
    SEQUENCE {
              pktcEUERSTNoAnsTOIndex      PktcEUETCRSTAppFeatIndexType,
              pktcEUERSTNoAnsTODuration   Unsigned32,
              pktcEUERSTNoAnsTOStatus     RowStatus
             }

pktcEUERSTNoAnsTOIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTNoAnsTimeoutEntry 1 }
 
pktcEUERSTNoAnsTODuration  OBJECT-TYPE 
    SYNTAX      Unsigned32 
    MAX-ACCESS  read-create 
    STATUS      current 
    DESCRIPTION 
        " This MIB Object specifies the No Answer Timeout Duration 
          in seconds." 
    REFERENCE "PacketCable Residential SIP Telephony Feature Specification" 
    ::= { pktcEUERSTNoAnsTimeoutEntry 2 } 
 
pktcEUERSTNoAnsTOStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNoAnsTimeoutEntry 3 }  
     
-- ---------------------------------------------------------------------            
-- Pktc EUE RST Caller ID Feature Profile 
-- Ref (PacketCable RST specification): " Caller ID Feature Data" 
-- ---------------------------------------------------------------------                     
pktcEUERSTCallerIdFeat  OBJECT IDENTIFIER ::= { pktcEUERSTFeatures 5 } 
 
-- The USER Caller ID Feature Table

pktcEUERSTCIDTable OBJECT-TYPE
    SYNTAX      SEQUENCE OF PktcEUERSTCIDEntry
    MAX-ACCESS  not-accessible
    STATUS      current
    DESCRIPTION
        " This data table represents User-based parameters
          associated with the Caller ID Feature for the 
          RST Service."
    ::= { pktcEUERSTCallerIdFeat 1 } 
    
pktcEUERSTCIDEntry OBJECT-TYPE
    SYNTAX      PktcEUERSTCIDEntry
    MAX-ACCESS  not-accessible
    STATUS      current
    DESCRIPTION
        " Each entry in this data table describes an association
          of a user with a Caller ID Feature parameter.
          Each entry in this table is stored in volatile memory."
    INDEX  { pktcEUERSTCIDIndex }
    ::= { pktcEUERSTCIDTable 1 } 
    
PktcEUERSTCIDEntry ::=
    SEQUENCE {
              pktcEUERSTCIDIndex      PktcEUETCRSTAppFeatIndexType,
              pktcEUERSTCIDPPS        INTEGER,
              pktcEUERSTCIDStatus     RowStatus
             }

pktcEUERSTCIDIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTCIDEntry 1 }
 
pktcEUERSTCIDPPS  OBJECT-TYPE 
    SYNTAX      INTEGER { 
                    anonymous(1), 
                    public(2) 
                } 
    MAX-ACCESS  read-create 
    STATUS      current 
    DESCRIPTION 
        " This MIB Object specifies the Permanent Presentation ActStatus." 
    REFERENCE "PacketCable Residential SIP Telephony Feature Specification" 
    ::= { pktcEUERSTCIDEntry 2 } 
 
pktcEUERSTCIDStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTCIDEntry 3 } 
    
-- ---------------------------------------------------------------------            
-- Pktc EUE RST Caller ID Display Feature Profile 
-- Ref (PacketCable RST specification): "Caller ID Display Feature Data" 
-- ---------------------------------------------------------------------                     

pktcEUERSTCIDDisFeat  OBJECT IDENTIFIER ::= { pktcEUERSTFeatures 6 } 
 
-- The USER Caller ID Display Feature Table

pktcEUERSTCIDDisTable OBJECT-TYPE
    SYNTAX      SEQUENCE OF PktcEUERSTCIDDisEntry
    MAX-ACCESS  not-accessible
    STATUS      current
    DESCRIPTION
        " This data table represents User-based parameters
          associated with the Caller ID Display Feature for the 
          RST Service."
    ::= { pktcEUERSTCIDDisFeat 1 } 
    
pktcEUERSTCIDDisEntry OBJECT-TYPE
    SYNTAX      PktcEUERSTCIDDisEntry
    MAX-ACCESS  not-accessible
    STATUS      current
    DESCRIPTION
        " Each entry in this data table describes an association
          of a user with a Caller ID Display Feature parameter.
          Each entry in this table is stored in volatile memory."
    INDEX  { pktcEUERSTCIDDisIndex }
    ::= { pktcEUERSTCIDDisTable 1 } 
    
PktcEUERSTCIDDisEntry ::=
    SEQUENCE {
              pktcEUERSTCIDDisIndex             PktcEUETCRSTAppFeatIndexType,
              pktcEUERSTCIDDisCNDActStat        TruthValue,   
              pktcEUERSTCIDDisCNAMDActStat      TruthValue,
              pktcEUERSTCIDDisDefCountry        SnmpAdminString,
              pktcEUERSTCIDDisStatus            RowStatus,
              pktcEUERSTCIDDisCIDCWActStat      TruthValue
             }

pktcEUERSTCIDDisIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTCIDDisEntry 1 }
 
pktcEUERSTCIDDisCNDActStat  OBJECT-TYPE 
    SYNTAX      TruthValue 
    MAX-ACCESS  read-create 
    STATUS      current 
    DESCRIPTION 
        " This MIB Object specifies the activation status for Calling  
          Number Display (CND)." 
    REFERENCE "PacketCable Residential SIP Telephony Feature Specification" 
    ::= { pktcEUERSTCIDDisEntry 2 }   
 
pktcEUERSTCIDDisCNAMDActStat  OBJECT-TYPE 
    SYNTAX      TruthValue  
    MAX-ACCESS  read-create 
    STATUS      current 
    DESCRIPTION 
        " This MIB Object specifies the activation status for Calling 
          Name Display (CNAMD)." 
    REFERENCE "PacketCable Residential SIP Telephony Feature Specification" 
    ::= { pktcEUERSTCIDDisEntry 3 }   
 
pktcEUERSTCIDDisDefCountry  OBJECT-TYPE 
    SYNTAX      SnmpAdminString 
    MAX-ACCESS  read-create 
    STATUS      current 
    DESCRIPTION 
        " This MIB Object specifies default country code." 
    REFERENCE "PacketCable Residential SIP Telephony Feature Specification" 
    ::= { pktcEUERSTCIDDisEntry 4 } 
    
pktcEUERSTCIDDisStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTCIDDisEntry 5 }

pktcEUERSTCIDDisCIDCWActStat  OBJECT-TYPE 
    SYNTAX      TruthValue 
    MAX-ACCESS  read-create 
    STATUS      current 
    DESCRIPTION 
        " This MIB Object specifies the activation status for the
          CIDCW feature.
          The value 'true' indicates CID Display and CW indication are 
          simultaneously active if both CID Display and CW features are 
          activated.
          The value 'false' indicated CID Display indication is disabled 
          if both CID and CW features are active.
          If CD Display is active but CW is not active, the EUE MUST ignore the
          value of this object."
    REFERENCE "PacketCable Residential SIP Telephony Feature Specification"
    DEFVAL { true }  
    ::= { pktcEUERSTCIDDisEntry 6 }    

--  Static objects

pktcEUERSTCIDDisTimeAdj  OBJECT-TYPE 
    SYNTAX      Integer32 
    UNITS       "minutes"
    MAX-ACCESS  read-write 
    STATUS      current 
    DESCRIPTION 
        " This MIB Object specifies the adjustment from location invariant
          time to time at current location.  The time delta in minutes.
          
          If not configured, this attribute takes the value of the 
          time zone acquired by the host system the UE resides or 
          defaults to 0. For example, an EUE reports the value of the
          RFC 2132 DHCP option 'time offset' (in minutes) from the CM.
          This attribute is ignored when pktcEUERSTCIDDisDSTInfo is not
          the zero-length string."
    REFERENCE "PacketCable Residential SIP Telephony Feature Specification" 
    ::= { pktcEUERSTCIDDisFeat 2 } 

pktcEUERSTCIDDisDSTFlag OBJECT-TYPE 
    SYNTAX      TruthValue 
    MAX-ACCESS  read-write 
    STATUS      current 
    DESCRIPTION 
        " The indication of Day Light Savings Time Shift
          When set to 'true' the eUE MUST apply the daylight Time 
          Savings Shifting i.e. apply a 1 hour adjustment during day 
          light savings time. When set to 'false' the eUE MUST NOT make
          any daylight Time Saving adjustment.
          This attribute is ignored when pktcEUERSTCIDDisDSTInfo is not
          the zero-length string."
    DEFVAL { true }  
    ::= { pktcEUERSTCIDDisFeat 3 }                

pktcEUERSTCIDDisDSTInfo OBJECT-TYPE 
    SYNTAX      SnmpAdminString 
    MAX-ACCESS  read-write 
    STATUS      current 
    DESCRIPTION 
        " The time zone option including DST information in the 
         'TZ-Posix String' format as defined in RFC 4833.
          If this attribute is not the zero-length string the UE MUST
          perform the time correction during the daylight saving time
          per this value and ignore the value of 
          pktcEUERSTCIDDisDSTFlag and pktcEUERSTCIDDisTimeAdj
          
          If not configured, this attribute takes the value of the 
          timezone acquired by the host system the UE resides or 
          defaults to the zero-length string. For example, an 
          EUE reports the value of the TZ-Posix string 
          provided in RFC 4833 DHCPv4 option 'TZ-POSIX String' or 
          DHCPv6 option code OPTION_NEW_POSIX_TIMEZONE from the CM.
          
          The following clarifications apply to the 'TZ-Posix String'
          expression: 
          Given the TZ-Posix String as : 
          stdoffset[dst[offset][,start[/time],end[/time]]]
          
          The EUE may ignore the time zone abbreviation associated with
          the 'std' and 'dst' expressions or may use them as part of a 
          particular time output formatting (e.g., display time with time
           zone local abbreviation). 
          The EUE is not required to support the parsing of the 'start'
          and 'end' expressions in Julian and zero-based Julian day.
          The EUE MUST apply the default values to the optional 
          components in the TZ-Posiz String." 
    ::= { pktcEUERSTCIDDisFeat 4 }      


-- ---------------------------------------------------------------------       
-- Pktc EUE RST Caller ID Per Call Blocking Feature Profile 
-- Ref (PacketCable RST specification): "Caller ID Per-Call Blocking Feature Data" 
-- ---------------------------------------------------------------------                     
pktcEUERSTCIDCallBlkFeat  OBJECT IDENTIFIER ::= { pktcEUERSTFeatures 7 } 
 
-- The USER Caller Call Block Feature Table

pktcEUERSTCallBlkTable OBJECT-TYPE
    SYNTAX      SEQUENCE OF PktcEUERSTCallBlkEntry
    MAX-ACCESS  not-accessible
    STATUS      current
    DESCRIPTION
        " This data table represents User-based parameters
          associated with the Call Block Feature for the 
          RST Service."
    ::= { pktcEUERSTCIDCallBlkFeat 1 } 
    
pktcEUERSTCallBlkEntry OBJECT-TYPE
    SYNTAX      PktcEUERSTCallBlkEntry
    MAX-ACCESS  not-accessible
    STATUS      current
    DESCRIPTION
        " Each entry in this data table describes an association
          of a user with a Call Block Feature parameter.
          Each entry in this table is stored in volatile memory."
    INDEX  { pktcEUERSTCIDBlkIndex }
    ::= { pktcEUERSTCallBlkTable 1 } 
    
PktcEUERSTCallBlkEntry ::=
    SEQUENCE {
              pktcEUERSTCIDBlkIndex           PktcEUETCRSTAppFeatIndexType,
              pktcEUERSTCIDCBlkConfTone       Uri,
              pktcEUERSTCIDCBlkErrTone        Uri,
              pktcEUERSTCIDCBlkStatus         RowStatus
             }

pktcEUERSTCIDBlkIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTCallBlkEntry 1 }
 
pktcEUERSTCIDCBlkConfTone  OBJECT-TYPE 
    SYNTAX      Uri 
    MAX-ACCESS  read-create 
    STATUS      current 
    DESCRIPTION 
        " This MIB Object specifies the confirmation tone after 
          vertical feature code." 
    REFERENCE "PacketCable Residential SIP Telephony Feature Specification" 
    ::= { pktcEUERSTCallBlkEntry 2 } 
                        
pktcEUERSTCIDCBlkErrTone  OBJECT-TYPE 
    SYNTAX      Uri 
    MAX-ACCESS  read-create 
    STATUS      current 
    DESCRIPTION 
        " This MIB Object specifies the error tone after 
          vertical feature code failure." 
    REFERENCE "PacketCable Residential SIP Telephony Feature Specification" 
    ::= { pktcEUERSTCallBlkEntry 3 } 

pktcEUERSTCIDCBlkStatus OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTCallBlkEntry 4 }           
          
 -- ---------------------------------------------------------------------       
 -- Pktc EUE RST Caller ID Per Call Delivery Feature Profile 
 -- Ref (PacketCable RST specification): "Caller ID Per-Call Delivery Feature  Data" 
 -- ---------------------------------------------------------------------                     
 pktcEUERSTCIDCallDelFeat  OBJECT IDENTIFIER ::= { pktcEUERSTFeatures 8 } 
  
 -- The USER Caller Call Delivery Feature Table

pktcEUERSTCallDelTable OBJECT-TYPE
    SYNTAX      SEQUENCE OF PktcEUERSTCallDelEntry
    MAX-ACCESS  not-accessible
    STATUS      current
    DESCRIPTION
        " This data table represents User-based parameters
          associated with the Call Delivery Feature for the 
          RST Service."
    ::= { pktcEUERSTCIDCallDelFeat 1 } 
    
pktcEUERSTCallDelEntry OBJECT-TYPE
    SYNTAX      PktcEUERSTCallDelEntry
    MAX-ACCESS  not-accessible
    STATUS      current
    DESCRIPTION
        " Each entry in this data table describes an association
          of a user with a Call Delivery Feature parameter.
          Each entry in this table is stored in volatile memory."
    INDEX  { pktcEUERSTCIDDelIndex }
    ::= { pktcEUERSTCallDelTable 1 } 
    
PktcEUERSTCallDelEntry ::=
    SEQUENCE {
              pktcEUERSTCIDDelIndex       PktcEUETCRSTAppFeatIndexType,
              pktcEUERSTCIDDelConfTone    Uri,
              pktcEUERSTCIDDelErrTone     Uri,
              pktcEUERSTCIDDelStatus      RowStatus
             }

pktcEUERSTCIDDelIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTCallDelEntry 1 }
 
pktcEUERSTCIDDelConfTone  OBJECT-TYPE 
     SYNTAX      Uri 
     MAX-ACCESS  read-create 
     STATUS      current 
     DESCRIPTION 
         " This MIB Object specifies the confirmation tone after 
           vertical feature code." 
     REFERENCE "PacketCable Residential SIP Telephony Feature Specification" 
     ::= { pktcEUERSTCallDelEntry 2 } 
                         
pktcEUERSTCIDDelErrTone  OBJECT-TYPE 
     SYNTAX      Uri 
     MAX-ACCESS  read-create 
     STATUS      current 
     DESCRIPTION 
         " This MIB Object specifies the error tone after 
           vertical feature code failure." 
     REFERENCE "PacketCable Residential SIP Telephony Feature Specification" 
     ::= { pktcEUERSTCallDelEntry 3 } 

pktcEUERSTCIDDelStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTCallDelEntry 4 }   
     
 -- ---------------------------------------------------------------------                     
 -- Pktc EUE RST Call Forwarding Variable Feature Profile 
 -- Ref (PacketCable RST specification): "Call Forwarding Variable Feature Data" 
 -- ---------------------------------------------------------------------                     
pktcEUERSTCFwdFeat  OBJECT IDENTIFIER ::= { pktcEUERSTFeatures 9 } 

-- The USER Call Forwarding Feature Table

pktcEUERSTCallFwdTable OBJECT-TYPE
    SYNTAX      SEQUENCE OF PktcEUERSTCallFwdEntry
    MAX-ACCESS  not-accessible
    STATUS      current
    DESCRIPTION
        " This data table represents User-based parameters
          associated with the Call Forwarding Feature for the 
          RST Service."
    ::= { pktcEUERSTCFwdFeat 1 } 
    
pktcEUERSTCallFwdEntry OBJECT-TYPE
    SYNTAX      PktcEUERSTCallFwdEntry
    MAX-ACCESS  not-accessible
    STATUS      current
    DESCRIPTION
        " Each entry in this data table describes an association
          of a user with a Call Forwarding Feature parameter.
          Each entry in this table is stored in volatile memory."
    INDEX  { pktcEUERSTCallFwdIndex }
    ::= { pktcEUERSTCallFwdTable 1 } 
    
PktcEUERSTCallFwdEntry ::=
    SEQUENCE {
              pktcEUERSTCallFwdIndex          PktcEUETCRSTAppFeatIndexType,
              pktcEUERSTCallFwdRingReminder   TruthValue,
              pktcEUERSTCallFwdSubDuration    Unsigned32,
              pktcEUERSTCallFwdAUID           PktcEUETCRSTAUID,
              pktcEUERSTCallFwdStatus         RowStatus   
             }

pktcEUERSTCallFwdIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTCallFwdEntry 1 }
 
pktcEUERSTCallFwdRingReminder  OBJECT-TYPE 
    SYNTAX      TruthValue 
    MAX-ACCESS  read-create 
    STATUS      current 
    DESCRIPTION 
        " This MIB Object specifies the Call Forward Ring Reminder." 
    REFERENCE "PacketCable Residential SIP Telephony Feature Specification" 
    ::= { pktcEUERSTCallFwdEntry 2 } 

pktcEUERSTCallFwdSubDuration  OBJECT-TYPE 
    SYNTAX      Unsigned32 
    MAX-ACCESS  read-create 
    STATUS      current 
    DESCRIPTION 
        " This MIB Object specifies the subscription duration in seconds." 
    REFERENCE "PacketCable Residential SIP Telephony Feature Specification" 
    ::= { pktcEUERSTCallFwdEntry 3 } 

pktcEUERSTCallFwdAUID   OBJECT-TYPE
    SYNTAX      PktcEUETCRSTAUID
    MAX-ACCESS  read-create 
    STATUS      current 
    DESCRIPTION 
        " This MIB Object defines the Application Unique Identifier (AUID)
          for this feature." 
    REFERENCE "PacketCable Residential SIP Telephony Feature Specification." 
    ::= { pktcEUERSTCallFwdEntry 4 } 
    
pktcEUERSTCallFwdStatus OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTCallFwdEntry 5 } 
          
-- The NETWORK Call Forwarding Feature Table            
                  
pktcEUERSTNfCallFwdTable OBJECT-TYPE 
    SYNTAX      SEQUENCE OF PktcEUERSTNfCallFwdEntry 
    MAX-ACCESS  not-accessible 
    STATUS      current 
    DESCRIPTION 
        " This data table represents the network-based Call Forwarding entries" 
    REFERENCE "PacketCable Residential SIP Telephony Feature Specification" 
    ::= { pktcEUERSTCFwdFeat 2 }  
     
pktcEUERSTNfCallFwdEntry OBJECT-TYPE 
    SYNTAX      PktcEUERSTNfCallFwdEntry 
    MAX-ACCESS  not-accessible 
    STATUS      current 
    DESCRIPTION 
        " Each entry in this table represents the Call Forwarding   
          entries. Each entry in this table is stored in volatile memory." 
    INDEX  {pktcEUEDevOpIndex} 
    ::= { pktcEUERSTNfCallFwdTable 1 }  
     
PktcEUERSTNfCallFwdEntry ::= 
    SEQUENCE { 
              pktcEUERSTNfCallFwdSpDialTone      TruthValue,
              pktcEUERSTNfCallFwdStatus          RowStatus 
             }
                
pktcEUERSTNfCallFwdSpDialTone  OBJECT-TYPE 
    SYNTAX      TruthValue 
    MAX-ACCESS  read-create 
    STATUS      current 
    DESCRIPTION 
        " This MIB Object specifies the special conditions dial tone 
          when forwarded indicator." 
    REFERENCE "PacketCable Residential SIP Telephony Feature Specification" 
    ::= { pktcEUERSTNfCallFwdEntry 1 } 
                                    
pktcEUERSTNfCallFwdStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNfCallFwdEntry 2 }   
               
-- ---------------------------------------------------------------------       
-- Pktc EUE RST Call Waiting Feature Data 
-- Ref (PacketCable RST specification): "Call Waiting Feature Data" 
-- --------------------------------------------------------------------- 
pktcEUERSTCallWaitFeat  OBJECT IDENTIFIER ::= { pktcEUERSTFeatures 10 } 

pktcEUERSTCallWaitTable OBJECT-TYPE
    SYNTAX      SEQUENCE OF PktcEUERSTCallWaitEntry
    MAX-ACCESS  not-accessible
    STATUS      current
    DESCRIPTION
        " This data table represents User-based parameters
          associated with the Call Waiting Feature for the 
          RST Service."
    ::= { pktcEUERSTCallWaitFeat 1 } 
    
pktcEUERSTCallWaitEntry OBJECT-TYPE
    SYNTAX      PktcEUERSTCallWaitEntry
    MAX-ACCESS  not-accessible
    STATUS      current
    DESCRIPTION
        " Each entry in this data table describes an association
          of a user with a Call Waiting Feature parameter.
          Each entry in this table is stored in volatile memory."
    INDEX  { pktcEUERSTCallWaitIndex }
    ::= { pktcEUERSTCallWaitTable 1 } 
    
PktcEUERSTCallWaitEntry ::=
    SEQUENCE {
              pktcEUERSTCallWaitIndex          PktcEUETCRSTAppFeatIndexType,
              pktcEUERSTCallWaitCancelEnable   TruthValue,
              pktcEUERSTCallWaitStatus         RowStatus,
              pktcEUERSTCallWaitDisconnectTiming Unsigned32   
             }

pktcEUERSTCallWaitIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTCallWaitEntry 1 }
 
pktcEUERSTCallWaitCancelEnable  OBJECT-TYPE 
    SYNTAX      TruthValue 
    MAX-ACCESS  read-create 
    STATUS      current 
    DESCRIPTION 
        " This MIB Object specifies the Call Wait Cancel hook flash 
        operations as described in the RST specification." 
    REFERENCE "PacketCable Residential SIP Telephony Feature Specification" 
    DEFVAL { true }
    ::= { pktcEUERSTCallWaitEntry 2 } 

pktcEUERSTCallWaitStatus OBJECT-TYPE 
    SYNTAX      RowStatus 
    MAX-ACCESS  read-create 
    STATUS      current 
    DESCRIPTION 
        " The status of this conceptual row.
          There is no restriction on the ability to change values in this 
          row while the row is active." 
    ::= { pktcEUERSTCallWaitEntry 3 } 

pktcEUERSTCallWaitDisconnectTiming OBJECT-TYPE
    SYNTAX Unsigned32
    UNITS "seconds"
    MAX-ACCESS read-create
    STATUS current
    DESCRIPTION
        " This MIB Object specifies the timer to resume a call with a third 
          party being held. The value '0' indicates immediate connect."
    DEFVAL { 10 }
    ::= { pktcEUERSTCallWaitEntry 4 }
                  
-- ---------------------------------------------------------------------       
-- Pktc EUE RST Call Hold Feature Profile 
-- Ref (PacketCable RST specification): "Call Hold Feature Data"  
-- ---------------------------------------------------------------------                     
pktcEUERSTCallHoldFeat  OBJECT IDENTIFIER ::= { pktcEUERSTFeatures 11 } 
 
-- The USER Call Hold Feature Table

pktcEUERSTCallHoldTable OBJECT-TYPE
    SYNTAX      SEQUENCE OF PktcEUERSTCallHoldEntry
    MAX-ACCESS  not-accessible
    STATUS      current
    DESCRIPTION
        " This data table represents User-based parameters
          associated with the Call Hold Feature for the 
          RST Service."
    ::= { pktcEUERSTCallHoldFeat 1 } 
    
pktcEUERSTCallHoldEntry OBJECT-TYPE
    SYNTAX      PktcEUERSTCallHoldEntry
    MAX-ACCESS  not-accessible
    STATUS      current
    DESCRIPTION
        " Each entry in this data table describes an association
          of a user with a Call Hold Feature parameter.
          Each entry in this table is stored in volatile memory."
    INDEX  { pktcEUERSTCHIndex }
    ::= { pktcEUERSTCallHoldTable 1 } 
    
PktcEUERSTCallHoldEntry ::=
    SEQUENCE {
              pktcEUERSTCHIndex          PktcEUETCRSTAppFeatIndexType,
              pktcEUERSTCHFeatConfirm    Uri,
              pktcEUERSTCHStatus         RowStatus
             }

pktcEUERSTCHIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTCallHoldEntry 1 }

pktcEUERSTCHFeatConfirm  OBJECT-TYPE 
    SYNTAX      Uri 
    MAX-ACCESS  read-create 
    STATUS      current 
    DESCRIPTION 
        " This MIB Object specifies the feature activation/deactivation 
          confirmation indicator." 
    REFERENCE "PacketCable Residential SIP Telephony Feature Specification" 
    ::= { pktcEUERSTCallHoldEntry 2 } 

pktcEUERSTCHStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTCallHoldEntry 3 }  
 
-- ---------------------------------------------------------------------           
-- Pktc EUE RST Call Transfer Feature Profile 
-- Ref (PacketCable RST specification): "Call Transfer Feature Data" 
-- ---------------------------------------------------------------------                     
pktcEUERSTCallXfrFeat  OBJECT IDENTIFIER ::= { pktcEUERSTFeatures 12 } 
 
-- The USER Call Transfer Feature Table

pktcEUERSTCallXfrTable OBJECT-TYPE
    SYNTAX      SEQUENCE OF PktcEUERSTCallXfrEntry
    MAX-ACCESS  not-accessible
    STATUS      current
    DESCRIPTION
        " This data table represents User-based parameters
          associated with the Call Hold Transfer for the 
          RST Service."
    ::= { pktcEUERSTCallXfrFeat 1 } 
    
pktcEUERSTCallXfrEntry OBJECT-TYPE
    SYNTAX      PktcEUERSTCallXfrEntry
    MAX-ACCESS  not-accessible
    STATUS      current
    DESCRIPTION
        " Each entry in this data table describes an association
          of a user with a Call Hold Transfer parameter.
          Each entry in this table is stored in volatile memory."
    INDEX  { pktcEUERSTCXIndex }
    ::= { pktcEUERSTCallXfrTable 1 } 
    
PktcEUERSTCallXfrEntry ::=
    SEQUENCE {
              pktcEUERSTCXIndex          PktcEUETCRSTAppFeatIndexType,
              pktcEUERSTCXNtfyTimeout    Unsigned32,
              pktcEUERSTCXStatus         RowStatus,
              pktcEUERSTCXInDialogRefer  TruthValue,
              pktcEUERSTCXIncomingOnly   TruthValue
             }

pktcEUERSTCXIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTCallXfrEntry 1 }

pktcEUERSTCXNtfyTimeout  OBJECT-TYPE 
    SYNTAX      Unsigned32 
    MAX-ACCESS  read-create 
    STATUS      current 
    DESCRIPTION 
        " This MIB Object specifies the Notify Timeout in seconds." 
    REFERENCE "PacketCable Residential SIP Telephony Feature Specification" 
    ::= { pktcEUERSTCallXfrEntry 2 }  
    
pktcEUERSTCXStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTCallXfrEntry 3 }

pktcEUERSTCXInDialogRefer OBJECT-TYPE
    SYNTAX TruthValue
    MAX-ACCESS read-create
    STATUS current
    DESCRIPTION
    " This MIB Object specifies the usage of call transfer
    refer. If set to 'true' a transfer via REFER is performed
    within the existing dialog with the transferee.
    If set to 'false' a transfer via REFER is sent out of
    dialog, to the transferee."
    REFERENCE "PacketCable Residential SIP Telephony Feature Specification"
    ::= { pktcEUERSTCallXfrEntry 4 }      
    
pktcEUERSTCXIncomingOnly OBJECT-TYPE
    SYNTAX TruthValue
    MAX-ACCESS read-create
    STATUS current
    DESCRIPTION
        " This MIB Object specifies whether call transfer can be invoked 
        only when the 1st call leg was an incoming call.
        
        If set to 'true' call transfer can be invoked only if the 1st call 
        leg was an incoming call. 
        
        If set to 'false' call transfer can be invoked if the 1st call leg 
        was an incoming or an outgoing call.
        
        The EUE MUST use the default value of 'false'."

    REFERENCE "PacketCable Residential SIP Telephony Feature Specification"
::= { pktcEUERSTCallXfrEntry 5 }
 
-- --------------------------------------------------------------------- 
-- Pktc EUE RST Do Not Disturb Feature Profile 
-- Ref (PacketCable RST specification): "DND Feature Data" 
-- --------------------------------------------------------------------- 
pktcEUERSTDnDFeat  OBJECT IDENTIFIER ::= { pktcEUERSTFeatures 13 } 
        
-- The USER Do Not Disturb Feature Table

pktcEUERSTDnDTable OBJECT-TYPE
    SYNTAX      SEQUENCE OF PktcEUERSTDnDEntry
    MAX-ACCESS  not-accessible
    STATUS      current
    DESCRIPTION
        " This data table represents User-based parameters
          associated with the Do Not Disturb feature for the 
          RST Service."
    ::= { pktcEUERSTDnDFeat 1 } 
    
pktcEUERSTDnDEntry OBJECT-TYPE
    SYNTAX      PktcEUERSTDnDEntry
    MAX-ACCESS  not-accessible
    STATUS      current
    DESCRIPTION
        " Each entry in this data table describes an association
          of a user with a Do Not Disturb parameter.
          Each entry in this table is stored in volatile memory."
    INDEX  { pktcEUERSTDnDIndex }
    ::= { pktcEUERSTDnDTable 1 } 
    
PktcEUERSTDnDEntry ::=
    SEQUENCE {
              pktcEUERSTDnDIndex            PktcEUETCRSTAppFeatIndexType,
              pktcEUERSTDnDActConfirm       Uri,
              pktcEUERSTDnDDeActConfirm     Uri,
              pktcEUERSTDnDAUID             PktcEUETCRSTAUID,
              pktcEUERSTDnDStatus           RowStatus
             }

pktcEUERSTDnDIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTDnDEntry 1 }

pktcEUERSTDnDActConfirm  OBJECT-TYPE 
    SYNTAX      Uri 
    MAX-ACCESS  read-create 
    STATUS      current 
    DESCRIPTION 
        " This MIB Object specifies the Feature Activation Confirmation 
          Indicator." 
    REFERENCE "PacketCable Residential SIP Telephony Feature Specification" 
    ::= { pktcEUERSTDnDEntry 2 } 
                       
pktcEUERSTDnDDeActConfirm  OBJECT-TYPE 
    SYNTAX      Uri 
    MAX-ACCESS  read-create 
    STATUS      current 
    DESCRIPTION 
        " This MIB Object specifies the Feature Deactivation Confirmation 
          Indicator." 
    REFERENCE "PacketCable Residential SIP Telephony Feature Specification" 
    ::= { pktcEUERSTDnDEntry 3 }   

pktcEUERSTDnDAUID   OBJECT-TYPE
    SYNTAX      PktcEUETCRSTAUID
    MAX-ACCESS  read-create 
    STATUS      current 
    DESCRIPTION 
        " This MIB Object defines the Application Unique Identifier (AUID)
          for this feature." 
    REFERENCE "PacketCable Residential SIP Telephony Feature Specification." 
    ::= { pktcEUERSTDnDEntry 4 } 
    
pktcEUERSTDnDStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTDnDEntry 5 }   
 
-- --------------------------------------------------------------------- 
-- Pktc EUE RST Subscriber Programmable PIN Feature Data 
-- Ref (PacketCable RST specification): "Subscriber Programmable PIN Feature Data" 
-- --------------------------------------------------------------------- 
-- No extension objects for this feature
 
-- --------------------------------------------------------------------- 
-- Pktc EUE RST MWI Feature Profile 
-- Ref (PacketCable RST specification): "MWI Feature Data" 
-- ---------------------------------------------------------------------       
pktcEUERSTMWIFeat  OBJECT IDENTIFIER ::= { pktcEUERSTFeatures 14 } 
                                 
-- The NETWORK MWI Feature Table            
                  
pktcEUERSTNfMWITable OBJECT-TYPE 
    SYNTAX      SEQUENCE OF PktcEUERSTNfMWIEntry 
    MAX-ACCESS  not-accessible 
    STATUS      current 
    DESCRIPTION 
        " This data table represents the network-based MWI entries" 
    REFERENCE "PacketCable Residential SIP Telephony Feature Specification" 
    ::= { pktcEUERSTMWIFeat 1 }  
     
pktcEUERSTNfMWIEntry OBJECT-TYPE 
    SYNTAX      PktcEUERSTNfMWIEntry 
    MAX-ACCESS  not-accessible 
    STATUS      current 
    DESCRIPTION 
        " Each entry in this table represents the MWI feature   
          entries. Each entry in this table is stored in volatile memory." 
    INDEX  {pktcEUEDevOpIndex} 
    ::= { pktcEUERSTNfMWITable 1 }  
        
PktcEUERSTNfMWIEntry ::=
    SEQUENCE {
              pktcEUERSTNfMWISubDuration    Unsigned32,
              pktcEUERSTNfMWIStatus         RowStatus        
             }

pktcEUERSTNfMWISubDuration  OBJECT-TYPE 
    SYNTAX      Unsigned32 
    UNITS       "seconds"
    MAX-ACCESS  read-create 
    STATUS      current 
    DESCRIPTION 
        " This MIB Object specifies the MWI Subscription duration." 
    REFERENCE "PacketCable Residential SIP Telephony Feature Specification" 
    ::= { pktcEUERSTNfMWIEntry 1 } 

pktcEUERSTNfMWIStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNfMWIEntry 2 }

-- --------------------------------------------------------------------- 
-- Pktc EUE RST Auto Recall Feature Profile 
-- Ref (PacketCable RST specification): "Auto Recall Feature Data" 
-- --------------------------------------------------------------------- 
pktcEUERSTAutoRclFeat  OBJECT IDENTIFIER ::= { pktcEUERSTFeatures 15 } 
  
-- The USER Auto Recall Feature Table

pktcEUERSTAutoRclTable OBJECT-TYPE
    SYNTAX      SEQUENCE OF PktcEUERSTAutoRclEntry
    MAX-ACCESS  not-accessible
    STATUS      current
    DESCRIPTION
        " This data table represents User-based parameters
          associated with the Auto Recall feature for the 
          RST Service."
    ::= { pktcEUERSTAutoRclFeat 1 } 
    
pktcEUERSTAutoRclEntry OBJECT-TYPE
    SYNTAX      PktcEUERSTAutoRclEntry
    MAX-ACCESS  not-accessible
    STATUS      current
    DESCRIPTION
        " Each entry in this data table describes an association
          of a user with an Auto Recall parameter.
          Each entry in this table is stored in volatile memory."
    INDEX  { pktcEUERSTARIndex }
    ::= { pktcEUERSTAutoRclTable 1 } 
    
PktcEUERSTAutoRclEntry ::=
    SEQUENCE {
              pktcEUERSTARIndex            PktcEUETCRSTAppFeatIndexType,
              pktcEUERSTARTimer            Unsigned32,
              pktcEUERSTARSpRngDuration    Unsigned32,
              pktcEUERSTARSpRngRetryTime   Unsigned32,
              pktcEUERSTARSpRngRetries     Unsigned32,
              pktcEUERSTARMaxSubSend       Unsigned32,
              pktcEUERSTARMaxSubRec        Unsigned32,
              pktcEUERSTARStatus           RowStatus                 
             }

pktcEUERSTARIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTAutoRclEntry 1 }

pktcEUERSTARTimer  OBJECT-TYPE 
    SYNTAX      Unsigned32 (0..1800) 
    UNITS       "seconds"
    MAX-ACCESS  read-create 
    STATUS      current 
    DESCRIPTION 
        " This MIB Object specifies the auto recall timer. 
          This is seconds of feature duration." 
    REFERENCE "PacketCable Residential SIP Telephony Feature Specification" 
    DEFVAL      {1800} 
    ::= { pktcEUERSTAutoRclEntry 2 } 
    
pktcEUERSTARSpRngDuration  OBJECT-TYPE 
    SYNTAX      Unsigned32  
    MAX-ACCESS  read-create 
    STATUS      current 
    DESCRIPTION 
        " This MIB Object specifies the auto recall special ring duration. 
          This is the number of special ringing ring cycles." 
    REFERENCE "PacketCable Residential SIP Telephony Feature Specification" 
    ::= { pktcEUERSTAutoRclEntry 3 } 
     
pktcEUERSTARSpRngRetryTime  OBJECT-TYPE 
    SYNTAX      Unsigned32  
    MAX-ACCESS  read-create 
    STATUS      current 
    DESCRIPTION 
        " This MIB Object specifies the auto recall special ringing retry 
          wait interval. This is seconds to wait between attempts to alert 
          the user with special ringing." 
    REFERENCE "PacketCable Residential SIP Telephony Feature Specification" 
    ::= { pktcEUERSTAutoRclEntry 4 } 
 
pktcEUERSTARSpRngRetries  OBJECT-TYPE 
    SYNTAX      Unsigned32  
    MAX-ACCESS  read-create 
    STATUS      current 
    DESCRIPTION 
        " This MIB Object specifies the number of auto recall special ringing  
          retries. 
          This is the number of times to retry special ringing before canceling 
          the AR request." 
    REFERENCE "PacketCable Residential SIP Telephony Feature Specification" 
    ::= { pktcEUERSTAutoRclEntry 5 } 
 
pktcEUERSTARMaxSubSend  OBJECT-TYPE 
    SYNTAX      Unsigned32  
    MAX-ACCESS  read-create 
    STATUS      current 
    DESCRIPTION 
        " This MIB Object specifies the maximum number of simultaneous  
          subscribes the EUE should send." 
    REFERENCE "PacketCable Residential SIP Telephony Feature Specification" 
    ::= { pktcEUERSTAutoRclEntry 6 } 
 
pktcEUERSTARMaxSubRec  OBJECT-TYPE 
    SYNTAX      Unsigned32  
    MAX-ACCESS  read-create 
    STATUS      current 
    DESCRIPTION 
        " This MIB Object specifies the maximum number of simultaneous  
          subscriptions the EUE should honor." 
    REFERENCE "PacketCable Residential SIP Telephony Feature Specification" 
    ::= { pktcEUERSTAutoRclEntry 7 } 
 
pktcEUERSTARStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTAutoRclEntry 8 }
     
-- --------------------------------------------------------------------- 
-- Pktc EUE RST Auto Callback Feature Profile 
-- Ref (PacketCable RST specification): "Auto Callback Feature Data" 
-- --------------------------------------------------------------------- 
pktcEUERSTAutoCbFeat  OBJECT IDENTIFIER ::= { pktcEUERSTFeatures 16 } 
                      
-- The USER Auto Callback Feature Table

pktcEUERSTAutoCbTable OBJECT-TYPE
    SYNTAX      SEQUENCE OF PktcEUERSTAutoCbEntry
    MAX-ACCESS  not-accessible
    STATUS      current
    DESCRIPTION
        " This data table represents User-based parameters
          associated with the Auto Callback feature for the 
          RST Service."
    ::= { pktcEUERSTAutoCbFeat 1 } 
    
pktcEUERSTAutoCbEntry OBJECT-TYPE
    SYNTAX      PktcEUERSTAutoCbEntry
    MAX-ACCESS  not-accessible
    STATUS      current
    DESCRIPTION
        " Each entry in this data table describes an association
          of a user with an Auto Callback parameter.
          Each entry in this table is stored in volatile memory."
    INDEX  { pktcEUERSTACbIndex }
    ::= { pktcEUERSTAutoCbTable 1 } 
    
PktcEUERSTAutoCbEntry ::=
    SEQUENCE {
              pktcEUERSTACbIndex            PktcEUETCRSTAppFeatIndexType,
              pktcEUERSTACbTimer            Unsigned32,
              pktcEUERSTACbSpRngDuration    Unsigned32,
              pktcEUERSTACbSpRngRetryTime   Unsigned32,
              pktcEUERSTACbSpRngRetries     Unsigned32,
              pktcEUERSTACbMaxSubSend       Unsigned32,
              pktcEUERSTACbMaxSubRec        Unsigned32,
              pktcEUERSTACbStatus           RowStatus                 
             }

pktcEUERSTACbIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTAutoCbEntry 1 }

pktcEUERSTACbTimer  OBJECT-TYPE 
    SYNTAX      Unsigned32 (0..1800) 
    UNITS       "seconds"
    MAX-ACCESS  read-create 
    STATUS      current 
    DESCRIPTION 
        " This MIB Object specifies the auto callback timer. 
          This is seconds of feature duration." 
    REFERENCE "PacketCable Residential SIP Telephony Feature Specification" 
    DEFVAL      {1800} 
    ::= { pktcEUERSTAutoCbEntry 2 } 

pktcEUERSTACbSpRngDuration  OBJECT-TYPE 
    SYNTAX      Unsigned32  
    MAX-ACCESS  read-create 
    STATUS      current 
    DESCRIPTION 
        " This MIB Object specifies the auto callback special ring duration. 
          This is the number of special ringing ring cycles." 
    REFERENCE "PacketCable Residential SIP Telephony Feature Specification" 
    ::= { pktcEUERSTAutoCbEntry 3 } 
     
pktcEUERSTACbSpRngRetryTime  OBJECT-TYPE 
    SYNTAX      Unsigned32  
    MAX-ACCESS  read-create 
    STATUS      current 
    DESCRIPTION 
        " This MIB Object specifies the auto callback special ringing retry 
          wait interval. This is seconds to wait between attempts to alert 
          the user with special ringing." 
    REFERENCE "PacketCable Residential SIP Telephony Feature Specification" 
    ::= { pktcEUERSTAutoCbEntry 4 } 
 
pktcEUERSTACbSpRngRetries  OBJECT-TYPE 
    SYNTAX      Unsigned32  
    MAX-ACCESS  read-create 
    STATUS      current 
    DESCRIPTION 
        " This MIB Object specifies the number of auto callback special ringing 
          retries. 
          This is the number of times to retry special ringing before canceling 
          the AR request." 
    REFERENCE "PacketCable Residential SIP Telephony Feature Specification" 
    ::= { pktcEUERSTAutoCbEntry 5 } 
 
pktcEUERSTACbMaxSubSend  OBJECT-TYPE 
    SYNTAX      Unsigned32  
    MAX-ACCESS  read-create 
    STATUS      current 
    DESCRIPTION 
        " This MIB Object specifies the maximum number of simultaneous  
          subscribes the EUE should send.." 
    REFERENCE "PacketCable Residential SIP Telephony Feature Specification" 
    ::= { pktcEUERSTAutoCbEntry 6 } 
 
pktcEUERSTACbMaxSubRec  OBJECT-TYPE 
    SYNTAX      Unsigned32  
    MAX-ACCESS  read-create 
    STATUS      current 
    DESCRIPTION 
        " This MIB Object specifies the maximum number of simultaneous 
          subscriptions the EUE should honor." 
    REFERENCE "PacketCable Residential SIP Telephony Feature Specification" 
    ::= { pktcEUERSTAutoCbEntry 7 } 
 
pktcEUERSTACbStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTAutoCbEntry 8 }
    
-- ---------------------------------------------------------------------       
-- Pktc EUE RST Busy Line Verify Feature Profile 
-- Ref (PacketCable RST specification): "Busy Line Verify Feature Data" 
-- ---------------------------------------------------------------------                     
pktcEUERSTBusyLineVFeat  OBJECT IDENTIFIER ::= { pktcEUERSTFeatures 17 } 
        
-- The NETWORK Busy Line Verify Feature Table            
                  
pktcEUERSTNfBusyLineVTable OBJECT-TYPE 
    SYNTAX      SEQUENCE OF PktcEUERSTNfBusyLineVEntry 
    MAX-ACCESS  not-accessible 
    STATUS      current 
    DESCRIPTION 
        " This data table represents the network-based Busy Line Verify
          Feature entries" 
    REFERENCE "PacketCable Residential SIP Telephony Feature Specification" 
    ::= { pktcEUERSTBusyLineVFeat 1 }  
     
pktcEUERSTNfBusyLineVEntry OBJECT-TYPE 
    SYNTAX      PktcEUERSTNfBusyLineVEntry 
    MAX-ACCESS  not-accessible 
    STATUS      current 
    DESCRIPTION 
        " Each entry in this table represents the Busy Line Verify feature   
          entries. Each entry in this table is stored in volatile memory." 
    INDEX  {pktcEUEDevOpIndex} 
    ::= { pktcEUERSTNfBusyLineVTable 1 }  
        
PktcEUERSTNfBusyLineVEntry ::=
    SEQUENCE {
              pktcEUERSTNfBLVOperId  SnmpAdminString,
              pktcEUERSTNfBLVStatus  RowStatus        
             }    
             
pktcEUERSTNfBLVOperId  OBJECT-TYPE 
    SYNTAX      SnmpAdminString 
    MAX-ACCESS  read-create 
    STATUS      current 
    DESCRIPTION 
        " This MIB Object specifies the Busy Line Verify Operator Id." 
    REFERENCE "PacketCable Residential SIP Telephony Feature Specification" 
    ::= { pktcEUERSTNfBusyLineVEntry 1 }
    
pktcEUERSTNfBLVStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNfBusyLineVEntry 2 } 
                        
-- --------------------------------------------------------------------- 
-- Pktc EUE RST Emergency Services Feature Profile 
-- Ref (PacketCable RST specification): "Emergency Services Feature Data" 
-- ---------------------------------------------------------------------                     
pktcEUERSTEmSvcFeat  OBJECT IDENTIFIER ::= { pktcEUERSTFeatures 18 } 
        
-- The NETWORK Emergency Services Feature Table            
                  
pktcEUERSTNfEmSvcTable OBJECT-TYPE 
    SYNTAX      SEQUENCE OF PktcEUERSTNfEmSvcEntry 
    MAX-ACCESS  not-accessible 
    STATUS      current 
    DESCRIPTION 
        " This data table represents the network-based Emergency Services
          Feature entries" 
    REFERENCE "PacketCable Residential SIP Telephony Feature Specification" 
    ::= { pktcEUERSTEmSvcFeat 1 }  
     
pktcEUERSTNfEmSvcEntry OBJECT-TYPE 
    SYNTAX      PktcEUERSTNfEmSvcEntry 
    MAX-ACCESS  not-accessible 
    STATUS      current 
    DESCRIPTION 
        " Each entry in this table represents the Emergency Services
          feature entries. Each entry in this table is stored in volatile
          memory." 
    INDEX  {pktcEUEDevOpIndex} 
    ::= { pktcEUERSTNfEmSvcTable 1 }  
        
PktcEUERSTNfEmSvcEntry ::=
    SEQUENCE {
              pktcEUERSTNfEmSvcNwHoldTimer   Unsigned32,
              pktcEUERSTNfEmSvcHowlTimer     Unsigned32, 
              pktcEUERSTNfEmSvcDSCPValMedia  Unsigned32,
              pktcEUERSTNfEmSvcDSCPValSig    Unsigned32,
              pktcEUERSTNfEmSvcStatus        RowStatus     
             }    

pktcEUERSTNfEmSvcNwHoldTimer  OBJECT-TYPE 
    SYNTAX      Unsigned32 
    MAX-ACCESS  read-create 
    STATUS      current 
    DESCRIPTION 
        " This MIB Object specifies the Emergency Services network hold 
          timer in minutes." 
    REFERENCE "PacketCable Residential SIP Telephony Feature Specification" 
    DEFVAL      {45} 
    ::= { pktcEUERSTNfEmSvcEntry 1 } 
   
pktcEUERSTNfEmSvcHowlTimer  OBJECT-TYPE 
    SYNTAX      Unsigned32 
    MAX-ACCESS  read-create 
    STATUS      current 
    DESCRIPTION 
        " This MIB Object specifies the Emergency Services howler 
          timer in seconds. " 
    REFERENCE "PacketCable Residential SIP Telephony Feature Specification" 
    DEFVAL      {3} 
    ::= { pktcEUERSTNfEmSvcEntry 2 } 
                  
pktcEUERSTNfEmSvcDSCPValMedia  OBJECT-TYPE 
    SYNTAX      Unsigned32 (0..63) 
    MAX-ACCESS  read-create 
    STATUS      current 
    DESCRIPTION 
        " This MIB Object specifies the DSCP Value for network packets 
        carrying the Media (RTP) information for Emergency Services." 
    REFERENCE "PacketCable Residential SIP Telephony Feature Specification" 
    ::= { pktcEUERSTNfEmSvcEntry 3 }    
         
pktcEUERSTNfEmSvcDSCPValSig  OBJECT-TYPE 
    SYNTAX      Unsigned32 (0..63) 
    MAX-ACCESS  read-create 
    STATUS      current 
    DESCRIPTION 
        " This MIB Object specifies the DSCP Value for network packets 
        carrying the Signaling information for Emergency Services." 
    REFERENCE "PacketCable Residential SIP Telephony Feature Specification" 
    ::= { pktcEUERSTNfEmSvcEntry 4 }    

pktcEUERSTNfEmSvcStatus  OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTNfEmSvcEntry 5 }  
    
 -- ---------------------------------------------------------------------                     
 -- Pktc EUE RST SCF Feature Profile 
 -- Ref (PacketCable RST specification): "SCF Feature Data" 
 -- ---------------------------------------------------------------------                     
pktcEUERSTSCFFeat  OBJECT IDENTIFIER ::= { pktcEUERSTFeatures 19 } 

-- The USER Call Forwarding Feature Table

pktcEUERSTSCFTable OBJECT-TYPE
    SYNTAX      SEQUENCE OF PktcEUERSTSCFEntry
    MAX-ACCESS  not-accessible
    STATUS      current
    DESCRIPTION
        " This data table represents User-based parameters
          associated with the RST SCF Feature." 
    ::= { pktcEUERSTSCFFeat 1 } 
    
pktcEUERSTSCFEntry OBJECT-TYPE
    SYNTAX      PktcEUERSTSCFEntry
    MAX-ACCESS  not-accessible
    STATUS      current
    DESCRIPTION
        " Each entry in this data table describes an association
          of a user with a SCF parameter.
          Each entry in this table is stored in volatile memory."
    INDEX  { pktcEUERSTSCFIndex }
    ::= { pktcEUERSTSCFTable 1 } 
    
PktcEUERSTSCFEntry ::=
    SEQUENCE {
              pktcEUERSTSCFIndex            PktcEUETCRSTAppFeatIndexType,
              pktcEUERSTSCFRingReminder     TruthValue,
              pktcEUERSTSCFAUID             PktcEUETCRSTAUID,
              pktcEUERSTSCFStatus           RowStatus
             }

pktcEUERSTSCFIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTSCFEntry 1 }
 
pktcEUERSTSCFRingReminder  OBJECT-TYPE 
    SYNTAX      TruthValue 
    MAX-ACCESS  read-create 
    STATUS      current 
    DESCRIPTION 
        " This MIB Object specifies the Call Forward Ring Reminder." 
    REFERENCE "PacketCable Residential SIP Telephony Feature Specification" 
    ::= { pktcEUERSTSCFEntry 2 } 

pktcEUERSTSCFAUID   OBJECT-TYPE
    SYNTAX      PktcEUETCRSTAUID
    MAX-ACCESS  read-create 
    STATUS      current 
    DESCRIPTION 
        " This MIB Object defines the Application Unique Identifier (AUID)
          for this feature." 
    REFERENCE "PacketCable Residential SIP Telephony Feature Specification." 
    ::= { pktcEUERSTSCFEntry 3 } 
    
pktcEUERSTSCFStatus OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTSCFEntry 4 }  

 -- ---------------------------------------------------------------------                     
 -- Pktc EUE RST Held Medial Feature Profile 
 -- Ref (PacketCable RST specification): "Held Media Feature Data" 
 -- ---------------------------------------------------------------------                     
pktcEUERSTHeldMediaFeat  OBJECT IDENTIFIER ::= { pktcEUERSTFeatures 20 } 

-- The USER Held Media Feature Table

pktcEUERSTHeldMediaTable OBJECT-TYPE
    SYNTAX      SEQUENCE OF PktcEUERSTHeldMediaEntry
    MAX-ACCESS  not-accessible
    STATUS      current
    DESCRIPTION
        " This object represents User-based parameters
          associated with the Held Media Feature." 
    ::= { pktcEUERSTHeldMediaFeat 1 } 
    
pktcEUERSTHeldMediaEntry OBJECT-TYPE
    SYNTAX      PktcEUERSTHeldMediaEntry
    MAX-ACCESS  not-accessible
    STATUS      current
    DESCRIPTION
        " Each entry in this data table describes an association
          of a user with a Held Media parameter.
          Each entry in this table is stored in volatile memory."
    INDEX  { pktcEUERSTHeldMediaIndex }
    ::= { pktcEUERSTHeldMediaTable 1 } 
    
PktcEUERSTHeldMediaEntry ::=
    SEQUENCE {
              pktcEUERSTHeldMediaIndex      PktcEUETCRSTAppFeatIndexType,
              pktcEUERSTHeldMediaEnabled    TruthValue,
              pktcEUERSTHeldMediaStatus           RowStatus
             }

pktcEUERSTHeldMediaIndex  OBJECT-TYPE
    SYNTAX      PktcEUETCRSTAppFeatIndexType
    MAX-ACCESS  not-accessible
    STATUS      current
    DESCRIPTION
        " This data element provides an index for the table.
          Values used for this index must be greater than zero
          and are not required to be sequential. This index 
          value may be provided as data in other objects that 
          reference this table."
    ::= { pktcEUERSTHeldMediaEntry 1 }
 
pktcEUERSTHeldMediaEnabled  OBJECT-TYPE 
    SYNTAX      TruthValue 
    MAX-ACCESS  read-create 
    STATUS      current 
    DESCRIPTION 
        " This MIB Object specifies the Held Media Condition
          'true' indicates local held is performed.
          'false' indicates network signaling is used for held media." 
    REFERENCE "PacketCable Residential SIP Telephony Feature Specification" 
    ::= { pktcEUERSTHeldMediaEntry 2 } 
    
pktcEUERSTHeldMediaStatus OBJECT-TYPE 
    SYNTAX      RowStatus 
    MAX-ACCESS  read-create 
    STATUS      current 
    DESCRIPTION 
        " The status of this conceptual row.
          There is no restriction on the ability to change values in this 
          row while the row is active.
          A created row can be set to active only after all corresponding
          instances of objects in the row have been set to valid values." 
    ::= { pktcEUERSTHeldMediaEntry 3 }

 -- ---------------------------------------------------------------------                     
 -- Pktc EUE RST Speed Dial Local Map Feature Profile 
 -- Ref (PacketCable RST specification): "Speed Dialing Feature" 
 -- ---------------------------------------------------------------------                     
pktcEUERSTSpeedDialLocalMapFeat  OBJECT IDENTIFIER ::= { pktcEUERSTFeatures 21 } 

-- The USER Speed Dial Local Map Table

pktcEUERSTSpeedDialLocalMapTable OBJECT-TYPE
    SYNTAX      SEQUENCE OF PktcEUERSTSpeedDialLocalMapEntry
    MAX-ACCESS  not-accessible
    STATUS      current
    DESCRIPTION
        " This object represents a local speed dial digit map.
        Digits are matched to instances of this object before 
        attempting to match digits from digit map." 
    ::= { pktcEUERSTSpeedDialLocalMapFeat 1 } 
    
pktcEUERSTSpeedDialLocalMapEntry OBJECT-TYPE
    SYNTAX      PktcEUERSTSpeedDialLocalMapEntry
    MAX-ACCESS  not-accessible
    STATUS      current
    DESCRIPTION
        " The conceptual row of pktcEUERSTSpeedDialLocalMapTable."
    REFERENCE "PacketCable RST Feature Specification"
    INDEX  { pktcEUERSTSpeedDialLocalMapIndex, pktcEUERSTSpeedDialLocalMapId }
    ::= { pktcEUERSTSpeedDialLocalMapTable 1 } 
    
PktcEUERSTSpeedDialLocalMapEntry ::=
    SEQUENCE {
              pktcEUERSTSpeedDialLocalMapIndex            PktcEUETCRSTAppFeatIndexType,
              pktcEUERSTSpeedDialLocalMapId               Unsigned32, 
              pktcEUERSTSpeedDialLocalMapCode             SnmpAdminString,
              pktcEUERSTSpeedDialLocalMapDigitString      SnmpAdminString,
              pktcEUERSTSpeedDialLocalMapStatus           RowStatus
             }

pktcEUERSTSpeedDialLocalMapIndex  OBJECT-TYPE
    SYNTAX      PktcEUETCRSTAppFeatIndexType
    MAX-ACCESS  not-accessible
    STATUS      current
    DESCRIPTION
        " This key represents the unique identifier of this
          instance. Values used for this index must be greater
          than zero and are not required to be sequential."
    ::= { pktcEUERSTSpeedDialLocalMapEntry 1 }

pktcEUERSTSpeedDialLocalMapId OBJECT-TYPE
    SYNTAX Unsigned32
    MAX-ACCESS not-accessible
    STATUS current
    DESCRIPTION
        " This attribute represent the unique identifier of an instance 
        within the scope of a local speed dial list."
    ::= { pktcEUERSTSpeedDialLocalMapEntry 2 }

 
pktcEUERSTSpeedDialLocalMapCode  OBJECT-TYPE 
    SYNTAX      SnmpAdminString 
    MAX-ACCESS  read-create 
    STATUS      current 
    DESCRIPTION
        "This attribute represents the one or two digit dialed speed
        call code
        The allowed values are:
        The ASCII code for numbers 2 to 9 for 1-digit speed calling
        The ASCII codes for numbers 20 to 99 for 2-digit speed calling." 
    REFERENCE "PacketCable RST Feature Specification"
    ::= { pktcEUERSTSpeedDialLocalMapEntry 3 } 
    
pktcEUERSTSpeedDialLocalMapDigitString  OBJECT-TYPE 
    SYNTAX      SnmpAdminString 
    MAX-ACCESS  read-create 
    STATUS      current 
    DESCRIPTION
        "This attribute represents the digit string associated 
         with the local Speed Dialing code to be matched in the 
         user digit map for call processing." 
    REFERENCE "PacketCable RST Feature Specification"
    ::= { pktcEUERSTSpeedDialLocalMapEntry 4 } 
    
        
pktcEUERSTSpeedDialLocalMapStatus OBJECT-TYPE 
    SYNTAX      RowStatus 
    MAX-ACCESS  read-create 
    STATUS      current 
    DESCRIPTION 
        " The status of this conceptual row.
          There is no restriction on the ability to change values in 
          this instance while is active.
          A created instance can be set to active only after all 
          corresponding attributes of the object instances have been
          set to valid values." 
    ::= { pktcEUERSTSpeedDialLocalMapEntry 5 }


 -- ---------------------------------------------------------------------                     
 -- Pktc EUE RST Hotline Feature Profile 
 -- Ref (PacketCable RST specification): "Hotline Feature" 
 -- ---------------------------------------------------------------------                     
pktcEUERSTHotlineFeat  OBJECT IDENTIFIER ::= { pktcEUERSTFeatures 22 } 

-- The Hot Line Table

pktcEUERSTHotlineTable OBJECT-TYPE
    SYNTAX      SEQUENCE OF PktcEUERSTHotlineEntry
    MAX-ACCESS  not-accessible
    STATUS      current
    DESCRIPTION
        " This object represents the hotline feature." 
    ::= { pktcEUERSTHotlineFeat 1 } 
    
pktcEUERSTHotlineEntry OBJECT-TYPE
    SYNTAX      PktcEUERSTHotlineEntry
    MAX-ACCESS  not-accessible
    STATUS      current
    DESCRIPTION
        " The conceptual row of pktcEUERSTHotlineTable."
    REFERENCE "PacketCable RST Feature Specification"
    INDEX  { pktcEUERSTHotlineIndex }
    ::= { pktcEUERSTHotlineTable 1 } 
    
PktcEUERSTHotlineEntry ::=
    SEQUENCE {
              pktcEUERSTHotlineIndex            PktcEUETCRSTAppFeatIndexType,
              pktcEUERSTHotlineDestAddress      SnmpAdminString,
              pktcEUERSTHotlineOffhookTimer     Unsigned32,
              pktcEUERSTHotlineStatus           RowStatus
             }

pktcEUERSTHotlineIndex  OBJECT-TYPE
    SYNTAX      PktcEUETCRSTAppFeatIndexType
    MAX-ACCESS  not-accessible
    STATUS      current
    DESCRIPTION
        " This key represents the unique identifier of this
          instance. Values used for this index must be greater
          than zero and are not required to be sequential."
    ::= { pktcEUERSTHotlineEntry 1 }
 
pktcEUERSTHotlineDestAddress  OBJECT-TYPE 
    SYNTAX      SnmpAdminString 
    MAX-ACCESS  read-create 
    STATUS      current 
    DESCRIPTION
        " This attribute represents the destination address 
          (SIP or TEL URI) where the active hotline feature 
          originates a call." 
    REFERENCE "PacketCable RST Feature Specification"
    ::= { pktcEUERSTHotlineEntry 2 } 
    
pktcEUERSTHotlineOffhookTimer  OBJECT-TYPE 
    SYNTAX      Unsigned32 
    UNITS       "seconds"
    MAX-ACCESS  read-create 
    STATUS      current 
    DESCRIPTION
        " This attribute represents the timer for activation of the 
          hotline call origination after offhook detection." 
    REFERENCE "PacketCable RST Feature Specification"
    DEFVAL { 0 } 
    ::= { pktcEUERSTHotlineEntry 3 } 
    
pktcEUERSTHotlineStatus OBJECT-TYPE 
    SYNTAX      RowStatus 
    MAX-ACCESS  read-create 
    STATUS      current 
    DESCRIPTION 
        " The status of this conceptual row.
          There is no restriction on the ability to change values in 
          this instance while is active.
          A created instance can be set to active only after all 
          corresponding attributes of the object instances have been
          set to valid values." 
    ::= { pktcEUERSTHotlineEntry 4 }

-- ---------------------------------------------------------------------
-- Pktc 3WC Feature Data
-- Ref (PacketCable RST specification): "3WC Feature Data"
-- ---------------------------------------------------------------------

pktcEUERST3WCallfeat OBJECT IDENTIFIER ::= { pktcEUERSTFeatures 23 }

pktcEUERST3WCallTable OBJECT-TYPE
    SYNTAX SEQUENCE OF PktcEUERST3WCallEntry
    MAX-ACCESS not-accessible
    STATUS current
    DESCRIPTION
        " This data table represents User-based parameters
          associated with the 3-way Call for the RST feature."
    ::= { pktcEUERST3WCallfeat 1 }

pktcEUERST3WCallEntry OBJECT-TYPE
    SYNTAX PktcEUERST3WCallEntry
    MAX-ACCESS not-accessible
    STATUS current
    DESCRIPTION
        " Each entry in this data table describes an association
          of a user with a 3-way Call Feature parameter.
          Each entry in this table is stored in volatile memory."
    INDEX { pktcEUERSTCallWaitIndex }
    ::= { pktcEUERST3WCallTable 1 }

PktcEUERST3WCallEntry ::=
    SEQUENCE {
               pktcEUERST3WCallIndex PktcEUETCRSTAppFeatIndexType,
               pktcEUERST3WCallDisconnectTiming Unsigned32,
               pktcEUERST3WCallStatus RowStatus
             }

pktcEUERST3WCallIndex OBJECT-TYPE
    SYNTAX PktcEUETCRSTAppFeatIndexType
    MAX-ACCESS not-accessible
    STATUS current
    DESCRIPTION
        " This data element provides an index for the table.
          Values used for this index must be greater than zero
          and are not required to be sequential. This index
          value may be provided as data in other objects that
          reference this table."
    ::= { pktcEUERST3WCallEntry 1 }

pktcEUERST3WCallDisconnectTiming OBJECT-TYPE
    SYNTAX Unsigned32
    MAX-ACCESS read-create
    STATUS current
    DESCRIPTION
        " This MIB Object specifies the timer reasume a call with a third
          party being held. The value '0' indicates immediate connect"
    REFERENCE "PacketCable Residential SIP Telephony Feature Specification"
    DEFVAL { 10 }
    ::= { pktcEUERST3WCallEntry 2 }

pktcEUERST3WCallStatus OBJECT-TYPE
    SYNTAX RowStatus
    MAX-ACCESS read-create
    STATUS current
    DESCRIPTION
        " The status of this conceptual row.
          There is no restriction on the ability to change values in this
          row while the row is active."
    ::= { pktcEUERST3WCallEntry 3 }

-- --------------------------------------------------------------------- 
-- Conformance Information  
-- --------------------------------------------------------------------- 
 
-- Compliance ActStatements 
pktcEUERSTCompliance MODULE-COMPLIANCE 
    STATUS      current 
    DESCRIPTION 
            "The compliance statement for implementations of the RST MIB
              Module." 
    MODULE   -- this module 
        MANDATORY-GROUPS { 
                 pktcEUERSTProfileGroup,
                 pktcEUERSTBasicCallGroup, 
                 pktcEUERSTUEStGroup, 
                 pktcEUERSTNoAnsGroup, 
                 pktcEUERSTCallerIDGroup, 
                 pktcEUERSTCallFwdGroup, 
                 pktcEUERSTCallHoldGroup, 
                 pktcEUERSTCallTransGroup, 
                 pktcEUERSTDNDGroup, 
                 pktcEUERSTMWIGroup, 
                 pktcEUERSTAutoRecallGroup, 
                 pktcEUERSTAutoCallbackGroup, 
                 pktcEUERSTBusyLineGroup, 
                 pktcEUERSTEmerSvcGroup, 
                 pktcEUERSTDigitMapGroup,
                 pktcEUERSTAppProfileGroup,
                 pktcEUERSTSCFProfileGroup,
                 pktcEUERSTHeldMediaGroup,
                 pktcEUERSTHotlineGroup,
                 pktcEUERSTCallWaitGroup,
                 pktcEUERST3WCallGroup
                 } 

    GROUP  pktcEUERSTAncGroup
    DESCRIPTION
        " This group is conditionally OPTIONAL. An EUE MUST implement 
          if and only if the MIB Objects of this group if an EUE supports 
          the Announcement Feature."
    
    GROUP pktcEUERSTSpeedDialLocalGroup
    DESCRIPTION
        " This group is conditionally OPTIONAL and implemented by the EUE
          only if the EUE supports the Speed Dial Local Map feature." 
          
    MODULE   PKTC-IETF-SIG-MIB  -- Group of the MIB Objects from RFC5098 
       MANDATORY-GROUPS {
                pktcSigDeviceGroup
       }

    OBJECT  pktcSigDevVmwiMode
    MIN-ACCESS  not-accessible
    DESCRIPTION
        " Object not applicable for the EUE."

    OBJECT  pktcSigCapabilityType
    MIN-ACCESS  not-accessible
    DESCRIPTION
        " Object not applicable for the EUE."

    OBJECT  pktcSigCapabilityVersion
    MIN-ACCESS  not-accessible
    DESCRIPTION
        " Object not applicable for the EUE."

    OBJECT  pktcSigCapabilityVendorExt
    MIN-ACCESS  not-accessible
    DESCRIPTION
        " Object not applicable for the EUE."

    OBJECT  pktcSigDefNcsReceiveUdpPort
    MIN-ACCESS  not-accessible
    DESCRIPTION
        " Object not applicable for the EUE."
          

    ::= { pktcEUERSTCompliances 1 }           

pktcEUERSTDeprecatedCompliance MODULE-COMPLIANCE 
    STATUS      deprecated 
    DESCRIPTION 
            "A placeholder for deprecated objects." 
    MODULE   -- this module 
         
    GROUP pktcEUERSTDeprecated
      DESCRIPTION
        " Deprecated list of  objects"
    ::= { pktcEUERSTCompliances 2 }  
    
 
pktcEUERSTEuroCompliance MODULE-COMPLIANCE  
    STATUS      current 
    DESCRIPTION 
            "The compliance statement for implementations of the RST MIB 
             Module in the European Technology Option of PacketCable 2.0." 
    MODULE   -- this module  
        MANDATORY-GROUPS {  
                 pktcEUERSTProfileGroup, 
                 pktcEUERSTBasicCallGroup, 
                 pktcEUERSTUEStGroup, 
                 pktcEUERSTNoAnsGroup, 
                 pktcEUERSTCallerIDGroup, 
                 pktcEUERSTCallFwdGroup, 
                 pktcEUERSTCallHoldGroup, 
                 pktcEUERSTCallTransGroup, 
                 pktcEUERSTDNDGroup, 
                 pktcEUERSTMWIGroup, 
                 pktcEUERSTAutoRecallGroup, 
                 pktcEUERSTAutoCallbackGroup, 
                 pktcEUERSTBusyLineGroup, 
                 pktcEUERSTEmerSvcGroup, 
                 pktcEUERSTDigitMapGroup, 
                 pktcEUERSTAppProfileGroup, 
                 pktcEUERSTSCFProfileGroup, 
                 pktcEUERSTHeldMediaGroup, 
                 pktcEUERSTHotlineGroup, 
                 pktcEUERSTCallWaitGroup, 
                 pktcEUERST3WCallGroup 
                 } 
 
    GROUP        pktcEUERSTAncGroup 
    DESCRIPTION 
         "This group is conditionally MANDATORY. An EUE MUST implement 
          the MIB Objects of this group if and only if an EUE supports 
          the Announcement Feature." 
     
    GROUP        pktcEUERSTSpeedDialLocalGroup 
    DESCRIPTION 
         "This group is conditionally MANDATORY. An EUE MUST implement 
          the MIB Objects of this group if and only if an EUE supports 
          the Speed Dial Local Map feature." 
           
    MODULE       PKTC-IETF-SIG-MIB  -- Group of MIB Objects from RFC5098 
       MANDATORY-GROUPS { 
                 pktcSigDeviceGroup, 
                 pktcInternationalGroup 
       } 
 
    OBJECT       pktcSigCapabilityType 
    MIN-ACCESS   not-accessible 
    DESCRIPTION 
         "Object not applicable for the EUE." 
 
    OBJECT       pktcSigCapabilityVersion 
    MIN-ACCESS   not-accessible 
    DESCRIPTION 
         "Object not applicable for the EUE." 
 
    OBJECT       pktcSigCapabilityVendorExt 
    MIN-ACCESS   not-accessible 
    DESCRIPTION 
         "Object not applicable for the EUE." 
 
    OBJECT       pktcSigDefNcsReceiveUdpPort 
    MIN-ACCESS   not-accessible 
    DESCRIPTION 
         "Object not applicable for the EUE." 
 
    OBJECT       pktcSigPulseSignalFrequency 
    MIN-ACCESS   not-accessible 
    DESCRIPTION 
         "Object not applicable for the EUE. Object is applicable if 
          optional feature of Pulse Dialing is supported" 
 
    OBJECT       pktcSigPulseSignalDbLevel 
    MIN-ACCESS   not-accessible 
    DESCRIPTION 
         "Object not applicable for the EUE. Object is applicable if 
          optional feature of Pulse Dialing is supported" 
 
    OBJECT       pktcSigPulseSignalDuration 
    MIN-ACCESS   not-accessible 
    DESCRIPTION 
         "Object not applicable for the EUE. Object is applicable if 
          optional feature of Pulse Dialing is supported" 
 
    OBJECT       pktcSigPulseSignalPulseInterval 
    MIN-ACCESS   not-accessible 
    DESCRIPTION 
         "Object not applicable for the EUE. Object is applicable if 
          optional feature of Pulse Dialing is supported" 
 
    OBJECT       pktcSigPulseSignalRepeatCount 
    MIN-ACCESS   not-accessible 
    DESCRIPTION 
         "Object not applicable for the EUE. Object is applicable if 
          optional feature of Pulse Dialing is supported" 
 
    OBJECT       pktcSigEndPntConfigPulseDialInterdigitTime 
    MIN-ACCESS   not-accessible 
    DESCRIPTION 
         "Object not applicable for the EUE. Object is applicable if 
          optional feature of Pulse Dialing is supported" 
 
    OBJECT       pktcSigEndPntConfigPulseDialMinMakeTime 
    MIN-ACCESS   not-accessible 
    DESCRIPTION 
         "Object not applicable for the EUE. Object is applicable if 
          optional feature of Pulse Dialing is supported" 
 
    OBJECT       pktcSigEndPntConfigPulseDialMaxMakeTime 
    MIN-ACCESS   not-accessible 
    DESCRIPTION 
         "Object not applicable for the EUE. Object is applicable if 
          optional feature of Pulse Dialing is supported" 
 
    OBJECT       pktcSigEndPntConfigPulseDialMinBreakTime 
    MIN-ACCESS   not-accessible 
    DESCRIPTION 
         "Object not applicable for the EUE. Object is applicable if 
          optional feature of Pulse Dialing is supported" 
 
    OBJECT       pktcSigEndPntConfigPulseDialMaxBreakTime 
    MIN-ACCESS   not-accessible 
    DESCRIPTION 
         "Object not applicable for the EUE. Object is applicable if 
          optional feature of Pulse Dialing is supported" 
 
    ::= { pktcEUERSTCompliances 3 } 
 
 
 
pktcEUERSTProfileGroup OBJECT-GROUP
      OBJECTS { 
         pktcEUERSTProfileVersion,
         pktcEUERSTKeepAliveSetting 
      }
      STATUS  current
      DESCRIPTION
            "The EUE RST Profile Group."
      ::= { pktcEUERSTGroups 1}
 
pktcEUERSTBasicCallGroup OBJECT-GROUP 
      OBJECTS {             
          pktcEUERSTBCallPrefCodecList,
          pktcEUERSTBCallStatus,
          pktcEUERSTNfBCallByeDelay,         
          pktcEUERSTNfBCallOrigDTTimer,      
          pktcEUERSTNfBCallTermOHErrSig,   
          pktcEUERSTNfBCallTermErrSigTimer,     
          pktcEUERSTNfBCallPermSeqTone1,     
          pktcEUERSTNfBCallPermSeqTimer1,    
          pktcEUERSTNfBCallPermSeqTone2,     
          pktcEUERSTNfBCallPermSeqTimer2,    
          pktcEUERSTNfBCallPermSeqTone3,     
          pktcEUERSTNfBCallPermSeqTimer3,    
          pktcEUERSTNfBCallLORTimer,
          pktcEUERSTNfBCallNEMDSCPValueMedia,
          pktcEUERSTNfBCallNEMDSCPValueSig,
          pktcEUERSTNfBCallStatus,
          pktcEUERSTNFBCallOrigModLongIntDig,
          pktcEUERSTNfBCallPermSeqTone4,
          pktcEUERSTNfBCallPermSeqTimer4,
          pktcEUERSTNfBCallOverrideNotifyRejected   
      } 
      STATUS  current 
      DESCRIPTION 
            "The RST Basic Call Group." 
      ::= { pktcEUERSTGroups 2} 

pktcEUERSTAncGroup OBJECT-GROUP 
      OBJECTS {             
          pktcEUERSTAncPrefLang,
          pktcEUERSTAncStatus,
          pktcEUERSTNfAncRes,
          pktcEUERSTNfAncDomain,
          pktcEUERSTNfAncPath,
          pktcEUERSTNfAncMIMEType,
          pktcEUERSTNfAncStatus,
          pktcEUERSTNfAncMapURI,
          pktcEUERSTNfAncMapStatus,
          pktcEUERSTNfAncMediaURI,
          pktcEUERSTNfAncMediaCachMaxAge,
          pktcEUERSTNfAncMediaStatus,
          pktcEUERSTNfAncLclMediaData,
          pktcEUERSTNfAncLclMediaType,
          pktcEUERSTNfAncLclMediaStatus          
      } 
      STATUS  current 
      DESCRIPTION 
            "The RST Announcement Group." 
      ::= { pktcEUERSTGroups 3}  
       
pktcEUERSTUEStGroup OBJECT-GROUP 
      OBJECTS {             
          pktcEUERSTUEActStatChgRegExp,
          pktcEUERSTUEActStatChgStatus
      } 
      STATUS  current 
      DESCRIPTION 
            "The RST EUE ActStatus Change Group." 
      ::= { pktcEUERSTGroups 4}  

pktcEUERSTNoAnsGroup OBJECT-GROUP 
      OBJECTS {             
          pktcEUERSTNoAnsTODuration,
          pktcEUERSTNoAnsTOStatus   
      } 
      STATUS  current 
      DESCRIPTION 
            "The RST No Answer Timeout Group." 
      ::= { pktcEUERSTGroups 5}  
     
pktcEUERSTCallerIDGroup OBJECT-GROUP 
      OBJECTS {             
          pktcEUERSTCIDPPS,
          pktcEUERSTCIDStatus,
          -- CID Display
          pktcEUERSTCIDDisTimeAdj,
          pktcEUERSTCIDDisDSTFlag,
          pktcEUERSTCIDDisDSTInfo,
          pktcEUERSTCIDDisCNDActStat,
          pktcEUERSTCIDDisCNAMDActStat,
          pktcEUERSTCIDDisDefCountry,
          pktcEUERSTCIDDisStatus,
          pktcEUERSTCIDDisCIDCWActStat,  
          -- CID per Blocking  
          pktcEUERSTCIDCBlkConfTone,
          pktcEUERSTCIDCBlkErrTone,
          pktcEUERSTCIDCBlkStatus,
          -- CID per Delivery 
          pktcEUERSTCIDDelConfTone,
          pktcEUERSTCIDDelErrTone,
          pktcEUERSTCIDDelStatus 
      } 
      STATUS  current 
      DESCRIPTION 
            "The RST Caller ID Group." 
      ::= { pktcEUERSTGroups 6}  
 
pktcEUERSTCallFwdGroup OBJECT-GROUP 
      OBJECTS {             
          pktcEUERSTCallFwdRingReminder,
          pktcEUERSTCallFwdSubDuration,
          pktcEUERSTCallFwdAUID,
          pktcEUERSTCallFwdStatus,
          pktcEUERSTNfCallFwdSpDialTone,
          pktcEUERSTNfCallFwdStatus
      } 
      STATUS  current 
      DESCRIPTION 
            "The RST Call Forward Group." 
      ::= { pktcEUERSTGroups 7} 

pktcEUERSTCallHoldGroup OBJECT-GROUP 
      OBJECTS {             
          pktcEUERSTCHFeatConfirm,
          pktcEUERSTCHStatus
      } 
      STATUS  current 
      DESCRIPTION 
            "The RST Call Hold Group." 
      ::= { pktcEUERSTGroups 8} 
       
pktcEUERSTCallTransGroup OBJECT-GROUP 
      OBJECTS {             
          pktcEUERSTCXNtfyTimeout,
          pktcEUERSTCXStatus,
          pktcEUERSTCXInDialogRefer,
          pktcEUERSTCXIncomingOnly
      } 
      
      STATUS  current 
      DESCRIPTION 
            "The RST Call Transfer Group." 
      ::= { pktcEUERSTGroups 9}  
       
pktcEUERSTDNDGroup OBJECT-GROUP 
      OBJECTS {             
          pktcEUERSTDnDActConfirm,
          pktcEUERSTDnDDeActConfirm,
          pktcEUERSTDnDAUID,
          pktcEUERSTDnDStatus 
      } 
      STATUS  current 
      DESCRIPTION 
            "The RST Do Not Disturb Group." 
      ::= { pktcEUERSTGroups 10} 
 
pktcEUERSTMWIGroup OBJECT-GROUP 
      OBJECTS {             
          pktcEUERSTNfMWISubDuration,
          pktcEUERSTNfMWIStatus
      } 
      STATUS  current 
      DESCRIPTION 
            "The RST MWI Group." 
      ::= { pktcEUERSTGroups 11} 

pktcEUERSTAutoRecallGroup OBJECT-GROUP 
      OBJECTS {             
          pktcEUERSTARTimer,
          pktcEUERSTARSpRngDuration,
          pktcEUERSTARSpRngRetryTime,
          pktcEUERSTARSpRngRetries,
          pktcEUERSTARMaxSubSend,
          pktcEUERSTARMaxSubRec,
          pktcEUERSTARStatus
      } 
      STATUS  current 
      DESCRIPTION 
            "The RST Auto Recall Group." 
      ::= { pktcEUERSTGroups 13} 
  
pktcEUERSTAutoCallbackGroup OBJECT-GROUP 
      OBJECTS {             
          pktcEUERSTACbTimer,
          pktcEUERSTACbSpRngDuration,
          pktcEUERSTACbSpRngRetryTime,
          pktcEUERSTACbSpRngRetries,
          pktcEUERSTACbMaxSubSend,
          pktcEUERSTACbMaxSubRec,
          pktcEUERSTACbStatus
      } 
      STATUS  current 
      DESCRIPTION 
            "The RST Auto Callback Group." 
      ::= { pktcEUERSTGroups 14} 
 
pktcEUERSTBusyLineGroup OBJECT-GROUP 
      OBJECTS {             
          pktcEUERSTNfBLVOperId,
          pktcEUERSTNfBLVStatus
      } 
      STATUS  current 
      DESCRIPTION 
            "The RST Busy Line Verify Group." 
      ::= { pktcEUERSTGroups 15} 
 
pktcEUERSTEmerSvcGroup OBJECT-GROUP 
      OBJECTS {             
          pktcEUERSTNfEmSvcNwHoldTimer,
          pktcEUERSTNfEmSvcHowlTimer, 
          pktcEUERSTNfEmSvcDSCPValMedia,
          pktcEUERSTNfEmSvcDSCPValSig,
          pktcEUERSTNfEmSvcStatus
      } 
      STATUS  current 
      DESCRIPTION 
            "The RST Emergency Services Group." 
      ::= { pktcEUERSTGroups 16}    

pktcEUERSTDigitMapGroup OBJECT-GROUP 
      OBJECTS {             
          pktcEUERSTDMValue,
          pktcEUERSTDMStatus,
          pktcEUERSTDigitMapVariableName,
          pktcEUERSTDigitMapVariableValue,
          pktcEUERSTDigitMapVariableStatus
      } 
      STATUS  current 
      DESCRIPTION 
            "The Digit Map Group." 
      ::= { pktcEUERSTGroups 17} 
      
pktcEUERSTAppProfileGroup OBJECT-GROUP 
      OBJECTS {         
          pktcEUERSTAppFeatID,
          pktcEUERSTAppFeatIndexRef,
          pktcEUERSTAppAdminStat,
          pktcEUERSTAppAdminStatInfo,
          pktcEUERSTAppOperStat,
          pktcEUERSTAppOperStatInfo,
          pktcEUERSTAppStatus
      } 
      STATUS  current 
      DESCRIPTION 
            "The App Profile Group." 
      ::= { pktcEUERSTGroups 18}

pktcEUERSTSCFProfileGroup OBJECT-GROUP 
      OBJECTS {         
          pktcEUERSTSCFRingReminder,
          pktcEUERSTSCFAUID,
          pktcEUERSTSCFStatus
      } 
      STATUS  current 
      DESCRIPTION 
            "The SCF Profile Group." 
      ::= { pktcEUERSTGroups 19}
      
pktcEUERSTHeldMediaGroup OBJECT-GROUP
       OBJECTS {
                           pktcEUERSTHeldMediaEnabled,
                           pktcEUERSTHeldMediaStatus
       }
       STATUS current
       DESCRIPTION
             "The Held Media Profile Group."
      ::= { pktcEUERSTGroups 20}             

pktcEUERSTSpeedDialLocalGroup OBJECT-GROUP
       OBJECTS {
                        pktcEUERSTSpeedDialLocalMapCode,
                        pktcEUERSTSpeedDialLocalMapDigitString,
                        pktcEUERSTSpeedDialLocalMapStatus
       }
       STATUS current
       DESCRIPTION
               "The Speed Dial Local Profile Group."
      ::= { pktcEUERSTGroups 21}            

pktcEUERSTHotlineGroup OBJECT-GROUP
       OBJECTS {
              pktcEUERSTHotlineDestAddress,
              pktcEUERSTHotlineOffhookTimer,
              pktcEUERSTHotlineStatus
       }
       STATUS current
       DESCRIPTION
               "The Hotline Profile Group."
      ::= { pktcEUERSTGroups 22}      

pktcEUERSTCallWaitGroup OBJECT-GROUP
       OBJECTS {
              pktcEUERSTCallWaitCancelEnable,
              pktcEUERSTCallWaitStatus,
              pktcEUERSTCallWaitDisconnectTiming
       }
       STATUS current
       DESCRIPTION
               "The Call Waiting Profile Group."
      ::= { pktcEUERSTGroups 23}
pktcEUERST3WCallGroup OBJECT-GROUP
       OBJECTS {
              pktcEUERST3WCallDisconnectTiming,
              pktcEUERST3WCallStatus
       }
       STATUS current
       DESCRIPTION
           "The Hotline Profile Group."
       ::= { pktcEUERSTGroups 24}

pktcEUERSTDeprecated OBJECT-GROUP
       OBJECTS {
              pktcEUERSTKeepAlive
               }
       STATUS deprecated
       DESCRIPTION
               "Deprecated MIB objects."
      ::= { pktcEUERSTGroups 25}             


END
