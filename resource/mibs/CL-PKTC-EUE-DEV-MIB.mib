-- *************************************************************************
-- 
--  Portions of this software Copyright (c) 2013 Broadcom Corporation
-- 
-- **************************************************************************
-- 
--  Filename: CL-PKTC-EUE-DEV-MIB.mib
-- 
-- **************************************************************************
--  Description:
--  The CL-PKTC-EUE-DEV-MIB with a correction to a formula error for TB in 
--  the description of pktcEUEDevPCSCFInviteAttempts introduced 
--  by ECN EUE-DATA-N-10.0644-2
-- **************************************************************************
--
CL-PKTC-EUE-DEV-MIB DEFINITIONS::= BEGIN

IMPORTS
    PktcEUETCCredsType,
    PktcEUETCCreds
                    FROM CL-PKTC-EUE-TC-MIB
    MODULE-IDENTITY,
    OBJECT-TYPE,
    Unsigned32
                    FROM SNMPv2-SMI

    OBJECT-GROUP,
    MODULE-COMPLIANCE
                    FROM SNMPv2-CONF
    
    TEXTUAL-CONVENTION,
    RowStatus, 
    TruthValue
                    FROM SNMPv2-TC
    SnmpAdminString
                    FROM SNMP-FRAMEWORK-MIB
    InetAddress,
    InetPortNumber,
    InetAddressDNS,
    InetAddressType,	
    InetVersion
                    FROM INET-ADDRESS-MIB
    pktcEUEMibs   
                    FROM CLAB-DEF-MIB;

    
pktcEUEDevMIB MODULE-IDENTITY
    LAST-UPDATED "201107110000Z" -- July 11, 2011
    ORGANIZATION "Cable Television Laboratories, Inc."
    CONTACT-INFO
            "Broadband Network Services
             Cable Television Laboratories, Inc.
             858 Coal Creek Circle,
             Louisville, CO 80027, USA 
             Phone: +1 303-661-9100
             Email: mibs@cablelabs.com
        
             Acknowledgements:
             Thomas Clack, Broadcom - Primary author,
             Eugene Nechamkin, Broadcom
             Sumanth Channabasappa, CableLabs
             John Berg, CableLabs
             Eduardo Cardona, CableLabs
             and members of the PacketCable PACM Focus Team."

    DESCRIPTION
            "This MIB module contains Configuration MIB 
             objects for the Embedded User Equipment (eUE)  as 
             required by the PacketCable E-UE Provisioning
             Framework Specification."
   REVISION "201107110000Z" -- July 11, 2011	
	 DESCRIPTION	
			"Revised Version includes ECN EUE-DATA-N-11.0661-6	
			and published as I06"
   REVISION "201012200000Z" -- Dec 20, 2010
    DESCRIPTION
            "Revised Version includes ECN EUE-DATA-N-10.10.0644-2
            and published as I06"      
   REVISION "201004260000Z" -- April 26, 2010
    DESCRIPTION
            "Revised Version includes ECN EUE-DATA-N-10.10.0633-2
            and published as I05"
   REVISION "200912140000Z" -- December 14, 2009
    DESCRIPTION
            "Revised Version includes ECN EUE-DATA-N-09.0605-5
            and published as I04"      
    REVISION "200905280000Z" -- May 28, 2009
    DESCRIPTION
            "Revised Version includes ECNs 
            EUE-DATA-N-08.0528-3
            EUE-DATA-N-09.0556-3
            and published as part of PKT-SP-EUE-DATA-I03-090528."
    REVISION "200807100000Z" -- July 10, 2008
    DESCRIPTION
            "Revised Version includes ECN EUE-DATA-N-08.0524-5
            and published as part of PKT-SP-EUE-DATA-I02-080710."            
    REVISION "200711060000Z" -- Nov 6, 2007
    DESCRIPTION
            "Initial version, published as part of the CableLabs
            E-UE Provisioning Data Model Specification
            PKT-SP-EUE-DATA-I01-071106
            Copyright 1999-2010 Cable Television Laboratories, Inc.
            All rights reserved."            
    ::= { pktcEUEMibs 3 }

-- ---------------------------------------------------------------------           
-- Pktc EUE DEV Textual Conventions 
-- ---------------------------------------------------------------------           

PktcEUEDevSipProtID ::= TEXTUAL-CONVENTION 
             STATUS  current 
             DESCRIPTION 
                 "This TEXTUAL CONVENTION is being defined 
                  as a way to enumerate the Protocols used for SIP." 
             SYNTAX   INTEGER { 
                               other(1),
                               udp(2),
                               tcp(3), 
                               tls(4)
                               }


-- Administrative assignments     
pktcEUEDevNotification      OBJECT IDENTIFIER ::= { pktcEUEDevMIB 0 } 
pktcEUEDevObjects           OBJECT IDENTIFIER ::= { pktcEUEDevMIB 1 } 
pktcEUEDevConformance       OBJECT IDENTIFIER ::= { pktcEUEDevMIB 2 } 

pktcEUEDevCompliances       OBJECT IDENTIFIER ::= { pktcEUEDevConformance 1 } 
pktcEUEDevGroups            OBJECT IDENTIFIER ::= { pktcEUEDevConformance 2 }




-- ---------------------------------------------------------------------           
--  eUE Profile Information
-- ---------------------------------------------------------------------           
pktcEUEDevProfile            OBJECT IDENTIFIER ::= { pktcEUEDevObjects 1 } 


pktcEUEDevProfileVersion OBJECT-TYPE
    SYNTAX      SnmpAdminString(SIZE(0..6))
    MAX-ACCESS  read-only
    STATUS      current
    DESCRIPTION
        " This MIB Object represents the Device Profile Version for this
          MIB module. The eUE MUST set this MIB Object to a value of '1.0'."
    ::= { pktcEUEDevProfile 1 }
    
-- ---------------------------------------------------------------------         
-- Operator Table
-- ---------------------------------------------------------------------         
pktcEUEDevOpTable OBJECT-TYPE
    SYNTAX      SEQUENCE OF PktcEUEDevOpEntry
    MAX-ACCESS  not-accessible
    STATUS      current
    DESCRIPTION
        " This data table contains Operator specific information
          associated with the eUE."
    ::= { pktcEUEDevProfile 2 }
    
pktcEUEDevOpEntry OBJECT-TYPE
    SYNTAX      PktcEUEDevOpEntry
    MAX-ACCESS  not-accessible
    STATUS      current
    DESCRIPTION
        " Each entry in this data table describes Operator
          parameters associated with a specific domain name.
         
          For each Operator that is associated with a user, 
          the corresponding parameters SHOULD be configured by 
          the Operator. 

          A domain name of '.' indicates any domain name.
        
          The eUE MUST use the values provided only for sessions
          established on behalf of the eUE identifier (e.g. eUE registration,
          eUE configuration, eUE Identifier based sessions).
          
          The conceptual rows MUST NOT persist across eUE resets."
    
    INDEX  { pktcEUEDevOpIndex }
    ::= { pktcEUEDevOpTable 1 } 
    
PktcEUEDevOpEntry ::=
    SEQUENCE {
             pktcEUEDevOpIndex               Unsigned32,
             pktcEUEDevOpDomain              InetAddressDNS,
             pktcEUEDevOpSTUNAddrType        InetAddressType,
             pktcEUEDevOpSTUNAddr            InetAddress,
             pktcEUEDevOpSTUNAddrPort        InetPortNumber,
             pktcEUEDevOpTURNAddrType        InetAddressType,
             pktcEUEDevOpTURNAddr            InetAddress,
             pktcEUEDevOpTURNAddrPort        InetPortNumber,
             pktcEUEDevOpTURNCredsType       PktcEUETCCredsType,
             pktcEUEDevOpTURNCreds           PktcEUETCCreds,
             pktcEUEDevOpRowStatus           RowStatus
             }
   

pktcEUEDevOpIndex OBJECT-TYPE
    SYNTAX      Unsigned32(1..16)
    MAX-ACCESS  not-accessible
    STATUS      current
    DESCRIPTION
        " A unique value used to identify an instance of a set of
          values pertaining to an Operator domain identified
          by 'pktcEUEDevOpDomain'. The indices SHOULD be contiguous.
          When multiple entries are specified, the eUE MUST give 
          precedence to the values indexed by lower indices."
    
    ::= { pktcEUEDevOpEntry 1 } 

pktcEUEDevOpDomain  OBJECT-TYPE
    SYNTAX      InetAddressDNS
    MAX-ACCESS  read-create
    STATUS      current
    DESCRIPTION
        " This data element contains the Operator's Domain or sub-domain 
          name. A value of '.' indicates any domainName."
    ::= { pktcEUEDevOpEntry 2 }

pktcEUEDevOpSTUNAddrType  OBJECT-TYPE
    SYNTAX      InetAddressType
    MAX-ACCESS  read-create
    STATUS      current
    DESCRIPTION
        " This data element identifies the data type of the 
          value contained in 'pktcEUEDevOpSTUNAddr'."
    
    DEFVAL   { unknown }
    ::= { pktcEUEDevOpEntry 3 }
 
pktcEUEDevOpSTUNAddr  OBJECT-TYPE
    SYNTAX      InetAddress
    MAX-ACCESS  read-create
    STATUS      current
    DESCRIPTION
        " This data element contains the STUN server address 
          associated with the domain name identified in 
          'pktcEUEDevOpDomain'."
    
    DEFVAL   { "" }
    ::= { pktcEUEDevOpEntry 4 }

pktcEUEDevOpSTUNAddrPort  OBJECT-TYPE
    SYNTAX      InetPortNumber
    MAX-ACCESS  read-create
    STATUS      current
    DESCRIPTION
        " This data element contains the STUN server port 
          associated with the server address identified in 
          'pktcEUEDevOpSTUNAddr'."
    
    DEFVAL   { 0 }
    ::= { pktcEUEDevOpEntry 5 }
    
pktcEUEDevOpTURNAddrType  OBJECT-TYPE
    SYNTAX      InetAddressType
    MAX-ACCESS  read-create
    STATUS      current
    DESCRIPTION
        " This data element identifies the data type of the 
          value contained in 'pktcEUEDevOpTURNAddr'."
    
    DEFVAL   { unknown }
    ::= { pktcEUEDevOpEntry 6 }
 
pktcEUEDevOpTURNAddr  OBJECT-TYPE
    SYNTAX      InetAddress
    MAX-ACCESS  read-create
    STATUS      current
    DESCRIPTION
        " This data element contains the TURN server address 
          associated with the domain name identified in 
          'pktcEUEDevOpDomain'."
    
    DEFVAL   { "" }
    ::= { pktcEUEDevOpEntry 7 }

pktcEUEDevOpTURNAddrPort  OBJECT-TYPE
    SYNTAX      InetPortNumber
    MAX-ACCESS  read-create
    STATUS      current
    DESCRIPTION
        " This data element contains the TURN server port 
          associated with the server address identified in 
          'pktcEUEDevOpTURNAddr'."
    
    DEFVAL   { 0 }
    ::= { pktcEUEDevOpEntry 8 }

pktcEUEDevOpTURNCredsType  OBJECT-TYPE
    SYNTAX      PktcEUETCCredsType
    MAX-ACCESS  read-create
    STATUS      current
    DESCRIPTION
        " This data element contains the creds type
          associated with the STUN Relay creds identified in 
          'pktcEUEDevOpTURNCreds'."
    DEFVAL   { none }
    ::= { pktcEUEDevOpEntry 9 } 

pktcEUEDevOpTURNCreds  OBJECT-TYPE
    SYNTAX      PktcEUETCCreds
    MAX-ACCESS  read-create
    STATUS      current
    DESCRIPTION
        " This optional data element MAY contain suitable credentials
          related to STUN Relay access.
          
          If read this data element MUST always return an empty 
          string value."
    DEFVAL   { "" }
    ::= { pktcEUEDevOpEntry 10 } 

    
pktcEUEDevOpRowStatus  OBJECT-TYPE
    SYNTAX      RowStatus
    MAX-ACCESS  read-create
    STATUS      current
    DESCRIPTION
        " This object defines the row status associated with the
          particular Operator in the pktcEUEDevOpTable.

          The value of this object has no effect on
          whether columnar objects in this row can be modified."
     ::= { pktcEUEDevOpEntry 11 }

-- ---------------------------------------------------------------------         
-- Operator domain names associated with a eUE
-- ---------------------------------------------------------------------          
pktcEUEDevDnsTable OBJECT-TYPE
    SYNTAX      SEQUENCE OF PktcEUEDevDnsEntry
    MAX-ACCESS  not-accessible
    STATUS      current
    DESCRIPTION
        " This data table represents the eUE's knowledge
          of suitable DNS Server information on a per Operator
          basis.
 
          The eUE MUST use the values provided only for sessions
          established on behalf of the eUE identifier (e.g. eUE P-CSCF Discovery,
          eUE registration, eUE configuration, eUE Identifier based sessions)."
 
    ::= { pktcEUEDevProfile 3 }
    
pktcEUEDevDnsEntry OBJECT-TYPE
    SYNTAX      PktcEUEDevDnsEntry
    MAX-ACCESS  not-accessible
    STATUS      current
    DESCRIPTION
        " Each entry in this data table contains an instance
          of a DNS Server entry for a given domain name as
          indicated by 'pktcEUEDevOpDomain'.

          The information in this table MAY be configured
          by the Operator.
          
          The conceptual rows MUST NOT persist across eUE resets."
    INDEX  { pktcEUEDevOpIndex, pktcEUEDevDnsIndex }
    ::= { pktcEUEDevDnsTable 1 } 
    
PktcEUEDevDnsEntry ::=
    SEQUENCE {
             pktcEUEDevDnsIndex          Unsigned32,
             pktcEUEDevDnsAddrType       InetAddressType,
             pktcEUEDevDnsAddr           InetAddress,
             pktcEUEDevDnsRowStatus      RowStatus
             } 
             
pktcEUEDevDnsIndex OBJECT-TYPE              
    SYNTAX      Unsigned32(1..16)
    MAX-ACCESS  not-accessible
    STATUS      current
    DESCRIPTION
        " A unique value used to identify an instance in this
          data table. The indices SHOULD be contiguous.
          When multiple entries are specified, the eUE MUST give 
          precedence to the values indexed by lower indices."
    ::= { pktcEUEDevDnsEntry 1 } 
      
pktcEUEDevDnsAddrType  OBJECT-TYPE
    SYNTAX      InetAddressType
    MAX-ACCESS  read-create
    STATUS      current
    DESCRIPTION
        " This data element contains the type of the data 
          element contained in 'pktcEUEDevDnsAddr'.
          The only valid values are 'ipv4' or 'ipv6'.
          The value 'unknown' may be used for row creation
          if the value of 'pktcEUEDevDnsAddr' is not specified."
    DEFVAL   { unknown }
    ::= { pktcEUEDevDnsEntry 2 }
    
pktcEUEDevDnsAddr  OBJECT-TYPE
    SYNTAX      InetAddress
    MAX-ACCESS  read-create
    STATUS      current
    DESCRIPTION
        " The IP address of a DNS server associated with
          the domain name indicated by the primary index 
          'pktcEUEDevOpIndex', for the instance indicated
          by the secondary index 'pktcEUEDevDnsIndex'.
          In the case this object is empty the eUE MUST use
          the DNS servers obtained via the DHCP process during 
          provisioning."
    DEFVAL   { "" }
    ::= { pktcEUEDevDnsEntry 3 }
             
pktcEUEDevDnsRowStatus  OBJECT-TYPE
    SYNTAX      RowStatus
    MAX-ACCESS  read-create
    STATUS      current
    DESCRIPTION
        " This object defines the row status associated with the
          particular Operator domain name in the pktcEUEDevDnsTable.

          The value of the 'pktcEUEDevDnsAddrType' object MUST not be
          modified while this object is 'active'.  The value of 
          'pktcEUEDevDnsAddr' MAY be modified while this object is active
          if the value is consistent with the type specified by the
          'pktcEUEDevDnsAddrType' object. The EUE MUST not allow the
          row to become 'active' unless the value of 'pktcEUEDevDnsAddr'
          is consistent with the value of 'pktcEUEDevDnsAddrType'."   
     ::= { pktcEUEDevDnsEntry 4 }
             

-- ---------------------------------------------------------------------        
-- P-CSCFs associated with the eUE
-- ---------------------------------------------------------------------       
pktcEUEDevPCSCFTable OBJECT-TYPE
    SYNTAX      SEQUENCE OF PktcEUEDevPCSCFEntry
    MAX-ACCESS  not-accessible
    STATUS      current
    DESCRIPTION
        " This data table represents the eUE's knowledge
          of suitable P-CSCFs information on a per Operator
          basis."

    ::= { pktcEUEDevProfile 4 }
    
pktcEUEDevPCSCFEntry OBJECT-TYPE
    SYNTAX      PktcEUEDevPCSCFEntry
    MAX-ACCESS  not-accessible
    STATUS      current
    DESCRIPTION
        " Each entry in this data table contains an instance
          of a P-CSCF Server entry for a given domain name.
          The information in this table MAY be configured
          by the Operator.

          The eUE MUST use the values provided only for sessions
          established on behalf of the eUE identifier (e.g. eUE registration,
          eUE configuration, eUE Identifier based sessions).
          
          The conceptual rows MUST NOT persist across eUE resets."

    INDEX  { pktcEUEDevOpIndex, pktcEUEDevPCSCFIndex }
    ::= { pktcEUEDevPCSCFTable 1 } 
    
PktcEUEDevPCSCFEntry ::=
    SEQUENCE {
             pktcEUEDevPCSCFIndex                Unsigned32,
             pktcEUEDevPCSCFAddrType             InetAddressType,
             pktcEUEDevPCSCFAddr                 InetAddress,
             pktcEUEDevPCSCFSipPort              InetPortNumber,
             pktcEUEDevPCSCFUsedProtocol         PktcEUEDevSipProtID,
             pktcEUEDevPCSCFUsedInetAddressType  InetAddressType,
             pktcEUEDevPCSCFUsedInetAddress      InetAddress,
             pktcEUEDevPCSCFTimerT1              Unsigned32,
             pktcEUEDevPCSCFTimerT2              Unsigned32,
             pktcEUEDevPCSCFTimerT4              Unsigned32,
             pktcEUEDevPCSCFTimerTD              Unsigned32,
             pktcEUEDevPCSCFRowStatus            RowStatus,
             pktcEUEDevPCSCFInviteAttempts       Unsigned32,
             pktcEUEDevPCSCFMaxTime              Unsigned32,
             pktcEUEDevPCSCFBaseTimeAllFailed    Unsigned32,
             pktcEUEDevPCSCFBaseTimeAllNotFailed Unsigned32,
             pktcEUEDevPCSCFSubscribeRetry       Unsigned32
             }
   
pktcEUEDevPCSCFIndex OBJECT-TYPE              
    SYNTAX      Unsigned32(1..16)
    MAX-ACCESS  not-accessible
    STATUS      current
    DESCRIPTION
        " A unique value used to identify an instance in this
          data table. The indices SHOULD be contiguous.
          When multiple entries are specified, the eUE MUST give 
          precedence to the values indexed by lower indices."

    ::= { pktcEUEDevPCSCFEntry 1 }
    
pktcEUEDevPCSCFAddrType  OBJECT-TYPE
    SYNTAX      InetAddressType
    MAX-ACCESS  read-create
    STATUS      current
    DESCRIPTION
        " This data element contains the type of the data 
          element contained in 'pktcEUEDevPCSCFAddr'."

    DEFVAL   { unknown }
    ::= { pktcEUEDevPCSCFEntry 2 }
    
pktcEUEDevPCSCFAddr  OBJECT-TYPE
    SYNTAX      InetAddress
    MAX-ACCESS  read-create
    STATUS      current
    DESCRIPTION
        " The IP address of a P-CSCF server associated with
          the domain name indicated by the primary index 
          'pktcEUEDevOpIndex', for the instance indicated
          by the secondary index 'pktcEUEDevPCSCFIndex'."

    DEFVAL   { "" }
    ::= { pktcEUEDevPCSCFEntry 3 }

pktcEUEDevPCSCFSipPort	OBJECT-TYPE
    SYNTAX      InetPortNumber
    MAX-ACCESS  read-create
    STATUS      current
    DESCRIPTION
        " This MIB Object contains a SIP Port to send the 
          SIP requests to (for the P-CSCF indicated by the 
          table entry).
          By default port 5060 is defined for SIP udp/tcp 
          transports and 5061 for tls."
    ::= { pktcEUEDevPCSCFEntry 4 }
      
pktcEUEDevPCSCFUsedProtocol  OBJECT-TYPE 
    SYNTAX      PktcEUEDevSipProtID
    MAX-ACCESS  read-create
    STATUS      current
    DESCRIPTION
        " This MIB Object contains a SIP Protocol which is 
          used by the EUE to communicate with the P-CSCF."
    ::= { pktcEUEDevPCSCFEntry 5 }

pktcEUEDevPCSCFUsedInetAddressType  OBJECT-TYPE
    SYNTAX      InetAddressType
    MAX-ACCESS  read-only
    STATUS      current
    DESCRIPTION
        " This MIB Object contains the Address Type of the P-CSCF 
          IP address used by the EUE in communication with the P-CSCF.
          Only ipv4 and ipv6 address types are valid values 
          for this MIB Object."
    ::= { pktcEUEDevPCSCFEntry 6 }

pktcEUEDevPCSCFUsedInetAddress OBJECT-TYPE
    SYNTAX      InetAddress
    MAX-ACCESS  read-only
    STATUS      current
    DESCRIPTION
        " This MIB Object contains the IP Address of the  
          P-CSCF used by the EUE. Only IPv4 and IPv6 addresses are
          valid values for this MIB Object."
    ::= { pktcEUEDevPCSCFEntry 7 }

pktcEUEDevPCSCFTimerT1  OBJECT-TYPE
    SYNTAX      Unsigned32
    UNITS       "milliseconds"
    MAX-ACCESS  read-create
    STATUS      current
    DESCRIPTION
        " This is the SIP Timer T1, an estimate for the round 
          trip time in the system (UE to P-CSCF). Please 
          refer to the PacketCable IMS Delta Session Initiation 
          Protocol (SIP) and Session Description Protocol (SDP), 
          Stage 3 Specification 3GPP TS 24.229 for more 
          information."
    REFERENCE 
       "PacketCable IMS Delta Session Initiation Protocol (SIP) 
        and Session Description Protocol (SDP), Stage 3 
        Specification 3GPP TS 24.229"
    DEFVAL {500}
    ::= { pktcEUEDevPCSCFEntry 8 }

pktcEUEDevPCSCFTimerT2  OBJECT-TYPE
    SYNTAX      Unsigned32
    UNITS       "milliseconds"
    MAX-ACCESS  read-create
    STATUS      current
    DESCRIPTION
        " This is the SIP Timer T2, an estimate for the maximum 
          retransmit interval for non-INVITE requests and INVITE 
          responses. Please refer to the PacketCable IMS Delta 
          Session Initiation Protocol (SIP) and Session Description 
          Protocol (SDP), Stage 3 Specification 3GPP TS 24.229
          for more information."
    REFERENCE 
       "PacketCable IMS Delta Session Initiation Protocol (SIP) 
        and Session Description Protocol (SDP), Stage 3 
        Specification 3GPP TS 24.229"
    DEFVAL {4000}
    ::= { pktcEUEDevPCSCFEntry 9 }

pktcEUEDevPCSCFTimerT4  OBJECT-TYPE
    SYNTAX      Unsigned32
    UNITS       "milliseconds"
    MAX-ACCESS  read-create
    STATUS      current
    DESCRIPTION
        " This is the SIP Timer TD, indicates the wait time
          for response retransmits.
          Please refer to the PacketCable IMS Delta Session 
          Initiation Protocol (SIP) and Session Description 
          Protocol (SDP), Stage 3 Specification 3GPP TS 24.229
          for more information."
    REFERENCE 
       "PacketCable IMS Delta Session Initiation Protocol (SIP) 
        and Session Description Protocol (SDP), Stage 3 
        Specification 3GPP TS 24.229"
    DEFVAL {5000}
    ::= { pktcEUEDevPCSCFEntry 10 }


pktcEUEDevPCSCFTimerTD  OBJECT-TYPE
    SYNTAX      Unsigned32 (0|32000..4294967295)
    UNITS       "milliseconds"
    MAX-ACCESS  read-create
    STATUS      current
    DESCRIPTION
        " This is the SIP Timer TD, an estimate for the maximum 
          duration a message will remain in the network.
          Please refer to the PacketCable IMS Delta Session 
          Initiation Protocol (SIP) and Session Description 
          Protocol (SDP), Stage 3 Specification 3GPP TS 24.229
          for more information.
          If the protocol used for a SIP Session is UDP this value is
          used for SIP Timer D, otherwise is ignored."
    REFERENCE 
       "PacketCable IMS Delta Session Initiation Protocol (SIP) 
        and Session Description Protocol (SDP), Stage 3 
        Specification 3GPP TS 24.229"
    DEFVAL {32000}
    ::= { pktcEUEDevPCSCFEntry 11 }

pktcEUEDevPCSCFRowStatus  OBJECT-TYPE
    SYNTAX      RowStatus
    MAX-ACCESS  read-create
    STATUS      current
    DESCRIPTION
        " This object defines the row status associated with the
          particular P-CSCF Server entry for the particular domain name.

          The value of the 'pktcEUEDevPCSCFAddrType' object MUST not be
          modified while this object is 'active'.  The value of 
          'pktcEUEDevPCSCFAddr' MAY be modified while this object is active
          if the value is consistent with the type specified by the
          'pktcEUEDevPCSCFAddrType' object."
     ::= { pktcEUEDevPCSCFEntry 12 }

pktcEUEDevPCSCFInviteAttempts  OBJECT-TYPE
    SYNTAX      Unsigned32 (1..7)
    UNITS       "attempts"
    MAX-ACCESS  read-create
    STATUS      current
    DESCRIPTION
        " This is the total number of INVITE message attempts before
          the SIP transaction is considered as failed due to no response.
          
          The total Timer TB MUST be derived from the total number of SIP 
          INVITE message attempts as follows:

          TB = [2^(n-1)]*T1
           
          n: total number of INVITE attempts
          T1 = Timer T1  
          
          For example, if the number of INVITE attempts is 3, (initial 
          INVITE + 2 retries)
          
          TB = [2^(3-1)]*0.5 =  2 secs.
          
          When the number of attempts is 7, timer B matches the Timer B 
          default value defined PacketCable IMS Delta Session Initiation 
          Protocol (SIP) and Session Description Protocol (SDP). 

          Please refer to the PacketCable IMS Delta Session Initiation 
          Protocol (SIP) and Session Description Protocol (SDP), 
          Stage 3 Specification 3GPP TS 24.229 for more 
          information.

          Note that this calculation for TB is custom for the
          Broadcom EDVA and is done in advance of an official change to
          the MIB description. "
    REFERENCE 
       "PacketCable IMS Delta Session Initiation Protocol (SIP) 
        and Session Description Protocol (SDP), Stage 3 
        Specification 3GPP TS 24.229"
    DEFVAL { 2 }
    ::= { pktcEUEDevPCSCFEntry 13 }     

pktcEUEDevPCSCFMaxTime  OBJECT-TYPE
    SYNTAX      Unsigned32
    UNITS       "seconds"
    MAX-ACCESS  read-create
    STATUS      current
    DESCRIPTION
        " This is the 'max-time' SIP Registration Recovery Timer 
          as defined in RFC 5626. 
          Please refer to the PacketCable IMS Delta Session 
          Initiation Protocol (SIP) and Session Description 
          Protocol (SDP), Stage 3 Specification 3GPP TS 24.229,
          and RFC 5626 for more information.
          If the protocol used for a SIP Session is UDP this value is
          used for SIP Timer D, otherwise is ignored."
    REFERENCE 
       "PacketCable IMS Delta Session Initiation Protocol (SIP) 
        and Session Description Protocol (SDP), Stage 3 
        Specification 3GPP TS 24.229"
    DEFVAL {1800}
    ::= { pktcEUEDevPCSCFEntry 14 }

pktcEUEDevPCSCFBaseTimeAllFailed  OBJECT-TYPE
    SYNTAX      Unsigned32
    UNITS       "seconds"
    MAX-ACCESS  read-create
    STATUS      current
    DESCRIPTION
        " This is the 'base-time (if all failed)' SIP Registration
          Recovery Timer as defined in RFC 5626. 
          Please refer to the PacketCable IMS Delta Session 
          Initiation Protocol (SIP) and Session Description 
          Protocol (SDP), Stage 3 Specification 3GPP TS 24.229,
          and RFC 5626 for more information.
          If the protocol used for a SIP Session is UDP this value is
          used for SIP Timer D, otherwise is ignored."
    REFERENCE 
       "PacketCable IMS Delta Session Initiation Protocol (SIP) 
        and Session Description Protocol (SDP), Stage 3 
        Specification 3GPP TS 24.229"
    DEFVAL {30}
    ::= { pktcEUEDevPCSCFEntry 15 }

pktcEUEDevPCSCFBaseTimeAllNotFailed  OBJECT-TYPE
    SYNTAX      Unsigned32
    UNITS       "seconds"
    MAX-ACCESS  read-create
    STATUS      current
    DESCRIPTION
        " This is the 'base-time (if all have not failed)' SIP 
          Registration Recovery Timer as defined in RFC 5626. 
          Please refer to the PacketCable IMS Delta Session 
          Initiation Protocol (SIP) and Session Description 
          Protocol (SDP), Stage 3 Specification 3GPP TS 24.229,
          and RFC 5626 for more information.
          If the protocol used for a SIP Session is UDP this value is
          used for SIP Timer D, otherwise is ignored."
    REFERENCE 
       "PacketCable IMS Delta Session Initiation Protocol (SIP) 
        and Session Description Protocol (SDP), Stage 3 
        Specification 3GPP TS 24.229"
    DEFVAL {90}
    ::= { pktcEUEDevPCSCFEntry 16 }

pktcEUEDevPCSCFSubscribeRetry  OBJECT-TYPE
    SYNTAX      Unsigned32
    UNITS       "seconds"
    MAX-ACCESS  read-create
    STATUS      current
    DESCRIPTION
        " This is the retry period for the initial SUBSCRIBE due to error
          responses, the absence of a retry period in the Retry-After
          header response or a request timeout. Please 
          refer to the PacketCable IMS Delta Session Initiation 
          Protocol (SIP) and Session Description Protocol (SDP), 
          Stage 3 Specification 3GPP TS 24.229 for more 
          information."
    REFERENCE 
       "PacketCable IMS Delta Session Initiation Protocol (SIP) 
        and Session Description Protocol (SDP), Stage 3 
        Specification 3GPP TS 24.229"
    DEFVAL {900}
    ::= { pktcEUEDevPCSCFEntry 17 }
    
-- ---------------------------------------------------------------------         
-- BSFs associated with a eUE
-- ---------------------------------------------------------------------         
pktcEUEDevBSFTable OBJECT-TYPE
    SYNTAX      SEQUENCE OF PktcEUEDevBSFEntry
    MAX-ACCESS  not-accessible
    STATUS      current
    DESCRIPTION
        " This data table represents the eUE's knowledge
          of suitable BSFs to contact."

    ::= { pktcEUEDevProfile 5 }
    
pktcEUEDevBSFEntry OBJECT-TYPE
    SYNTAX      PktcEUEDevBSFEntry
    MAX-ACCESS  not-accessible
    STATUS      current
    DESCRIPTION
        " Each entry in this data table contains an instance
          of a BSF, specific to a AS type, for a given Operator's
          Domain Name.
          The entries represent the eUE's knowledge
          of suitable BSFs to contact, as per the IMS GBA
          architecture to obtain credentials and enabling secure 
          sessions to Application Servers. A list of 
          BSFs for each Operator and application
          types MAY be configured by the Operator.
          
          The conceptual rows MUST NOT persist across eUE resets."

    INDEX  { pktcEUEDevOpIndex, pktcEUEDevBSFASType, pktcEUEDevBSFIndex }
    ::= { pktcEUEDevBSFTable 1 } 
    
PktcEUEDevBSFEntry ::=
    SEQUENCE {
             pktcEUEDevBSFASType     SnmpAdminString,
             pktcEUEDevBSFIndex      Unsigned32,
             pktcEUEDevBSFAddrType   InetAddressType,
             pktcEUEDevBSFAddr       InetAddress,
             pktcEUEDevBSFRowStatus  RowStatus
             }
   
pktcEUEDevBSFASType OBJECT-TYPE              
    SYNTAX      SnmpAdminString (SIZE (0..108))
    MAX-ACCESS  not-accessible
    STATUS      current
    DESCRIPTION
        " A unique value used to indicate the AS type to 
          which the BSFs correspond.
          Applications using GBA are required to specify
          such identifiers explicitly."

    ::= { pktcEUEDevBSFEntry 1 }
    
pktcEUEDevBSFIndex OBJECT-TYPE              
    SYNTAX      Unsigned32 (1..16)
    MAX-ACCESS  not-accessible
    STATUS      current
    DESCRIPTION
        " A unique value used to identify an instance in this
          data table. The indices SHOULD be contiguous.
          When multiple entries are specified, the eUE MUST give 
          precedence to the values indexed by lower indices."

    ::= { pktcEUEDevBSFEntry 2 }
    
pktcEUEDevBSFAddrType  OBJECT-TYPE
    SYNTAX      InetAddressType
    MAX-ACCESS  read-only
    STATUS      current
    DESCRIPTION
        " This data element contains the type of the data 
          element contained in 'pktcEUEDevBSFAddr'."

    DEFVAL   { unknown }
    ::= { pktcEUEDevBSFEntry 3 }
    
pktcEUEDevBSFAddr  OBJECT-TYPE
    SYNTAX      InetAddress
    MAX-ACCESS  read-only
    STATUS      current
    DESCRIPTION
        " The address of a BSF server associated with
          the domain name indicated by the indices
          'pktcEUEDevOpIndex' (Operator Domain),
          'pktcEUEDevBSFASType' and 'pktcEUEDevBSFIndex'."

    DEFVAL   { "" }
    ::= { pktcEUEDevBSFEntry 4 }

pktcEUEDevBSFRowStatus  OBJECT-TYPE
    SYNTAX      RowStatus
    MAX-ACCESS  read-create
    STATUS      current
    DESCRIPTION
        " This object defines the row status associated with this
          instance of a BSF.

          The value of the 'pktcEUEDevBSFAddrType' object MUST not be
          modified while this object is 'active'.  The value of 
          'pktcEUEDevBSFAddr' MAY be modified while this object is active
          if the value is consistent with the type specified by the
          'pktcEUEDevBSFAddrType' object."
     ::= { pktcEUEDevBSFEntry 5 }
      
-- ---------------------------------------------------------------------        
-- Certificate Bootstrapping Data
-- ---------------------------------------------------------------------        
pktcEUECBSupport OBJECT-TYPE
    SYNTAX      TruthValue
    MAX-ACCESS  read-only
    STATUS      current
    DESCRIPTION
        "This MIB Object is used by the eUE to report 
         support for Certificate Bootstrapping.
         If the MIB Object is set to a value of true(1)
         it indicates that the device supports Certificate
         Bootstrapping.
         If the MIB Object is set to a value of false(1)
         it indicates that the device does not support
         Certificate Bootstrapping."
    ::= { pktcEUEDevProfile 6 }

pktcEUECBEnable OBJECT-TYPE
    SYNTAX      TruthValue
    MAX-ACCESS  read-write
    STATUS      current
    DESCRIPTION
        "This MIB Object is used to initiate the Certificate
         Bootstrapping procedure in an eUE.

         If this value is set to a value of true(1) and the
         MIB Object pktcEUECBData contains a non-zero HTTP/HTTPS
         URI, then the eUE MUST initiate the Certificate
         Bootstrapping procedure, if supported.

         If the eUE does not support the Certificate
         Bootstrapping procedure, it rejects any attempt
         to set this MIB Object to a value of true(1).
         The eUE MUST return a value of false(2) when this
         MIB Object is read.

         If the Certificate Bootstrapping procedure was
         successful, the eUE MUST act on the Certificate
         Bootstrapping configuration file provided. 

         If the procedure was unsuccessful (e.g., 
         authentication error or unresponsive server),
         the eUE MUST report the corresponding management
         event."
    DEFVAL {false}
    ::= { pktcEUEDevProfile 7 }

pktcEUECBData OBJECT-TYPE
    SYNTAX      OCTET STRING(SIZE(0..1023))
    MAX-ACCESS  read-write
    STATUS      current
    DESCRIPTION
        "This MIB Object contains a HTTP/HTTPS URI to be used for
         Certificate Bootstrapping. Any attempt to set it to 
         anything other than a HTTP/HTTPS URI MUST be rejected
         by the eUE."
    ::= { pktcEUEDevProfile 8 }

-- ---------------------------------------------------------------------          
-- Scalar MIB Objects for the EUE Device
-- ---------------------------------------------------------------------          

pktcEUEDevSipPort OBJECT-TYPE
    SYNTAX      InetPortNumber
    MAX-ACCESS  read-write
    STATUS      current
    DESCRIPTION
        "This MIB Object contains the SIP Port to receive the
         SIP Requests on."
    DEFVAL { 5060 }
    ::= { pktcEUEDevProfile 9 }

pktcEUEPreferredCandidatePair OBJECT-TYPE
    SYNTAX      InetVersion
    MAX-ACCESS  read-write
    STATUS      current
    DESCRIPTION
        "This MIB Object identifies the preferred IP version to be used
        when selecting the valid candidate pair for a media stream.
 	    
         The following requirements apply depending on the value of
         this MIB Object:

         - 'ipv4'
         The eUE MUST prefer IPv4 for media.
         
         - 'ipv6'
         The eUE MUST prefer IPv6 for media.
         
         - 'unknown'
          The eUE MUST prefer the IP version for media that matches
          the IP version of the primary IP address."

    REFERENCE 
        "PacketCable IMS Delta Session Initiation Protocol (SIP)  
        and Session Description Protocol (SDP), Stage 3  
        Specification 3GPP TS 24.229."
    
    DEFVAL { unknown }
    ::= { pktcEUEDevProfile 10 }
    
-- ---------------------------------------------------------------------
-- Conformance Information
-- ---------------------------------------------------------------------


-- ----------------------
-- Compliance Statements
-- ----------------------
pktcEUEDevMIBCompliance MODULE-COMPLIANCE
    STATUS      current
    DESCRIPTION
        " The compliance statement for implementations of the eUE MIB."
    MODULE   
        MANDATORY-GROUPS {
                       pktcEUEDevProfileGroup,
		          pktcEUEDevOpGroup,
		          pktcEUEDevDnsGroup,
		          pktcEUEDevPCSCFGroup,
		          pktcEUEDevBSFGroup,
		          pktcEUEDevPerDeviceGroup
                         }

    ::= { pktcEUEDevCompliances 1 }

pktcEUEDevProfileGroup OBJECT-GROUP
      OBJECTS { 
         pktcEUEDevProfileVersion
      }
      STATUS  current
      DESCRIPTION
            "The eUE Device Profile Group."
      ::= { pktcEUEDevGroups 1}

pktcEUEDevOpGroup OBJECT-GROUP
      OBJECTS { 
         pktcEUEDevOpDomain,
         pktcEUEDevOpSTUNAddrType,
         pktcEUEDevOpSTUNAddr,
         pktcEUEDevOpSTUNAddrPort,
         pktcEUEDevOpTURNAddrType,
         pktcEUEDevOpTURNAddr,
         pktcEUEDevOpTURNAddrPort,
         pktcEUEDevOpTURNCredsType,
         pktcEUEDevOpTURNCreds,
         pktcEUEDevOpRowStatus
      }
      STATUS  current
      DESCRIPTION
            "The eUE Operator Group."
      ::= { pktcEUEDevGroups 2} 
        
pktcEUEDevDnsGroup OBJECT-GROUP
      OBJECTS { 
         pktcEUEDevDnsAddrType,
         pktcEUEDevDnsAddr,
         pktcEUEDevDnsRowStatus             
      }
      STATUS  current
      DESCRIPTION
            "The eUE DNS Group."
      ::= { pktcEUEDevGroups 3}  
      
pktcEUEDevPCSCFGroup OBJECT-GROUP
      OBJECTS { 
         pktcEUEDevPCSCFAddrType,
         pktcEUEDevPCSCFAddr,
         pktcEUEDevPCSCFSipPort,
         pktcEUEDevPCSCFUsedProtocol,
         pktcEUEDevPCSCFUsedInetAddressType,
         pktcEUEDevPCSCFUsedInetAddress,
         pktcEUEDevPCSCFTimerT1,
         pktcEUEDevPCSCFTimerT2,
         pktcEUEDevPCSCFTimerT4,
         pktcEUEDevPCSCFTimerTD,
         pktcEUEDevPCSCFRowStatus,
         pktcEUEDevPCSCFInviteAttempts,
         pktcEUEDevPCSCFMaxTime,
         pktcEUEDevPCSCFBaseTimeAllFailed,
         pktcEUEDevPCSCFBaseTimeAllNotFailed,
         pktcEUEDevPCSCFSubscribeRetry
      }
      STATUS  current
      DESCRIPTION
            "The eUE P-CSCF Group."
      ::= { pktcEUEDevGroups 4}

pktcEUEDevBSFGroup OBJECT-GROUP
      OBJECTS { 
         pktcEUEDevBSFAddrType,
         pktcEUEDevBSFAddr,
         pktcEUEDevBSFRowStatus
      }
      STATUS  current
      DESCRIPTION
            "The eUE BSF Group."
      ::= { pktcEUEDevGroups 5}


pktcEUEDevPerDeviceGroup  OBJECT-GROUP
      OBJECTS { 
         pktcEUECBSupport,
         pktcEUECBEnable,
         pktcEUECBData,
         pktcEUEDevSipPort,
         pktcEUEPreferredCandidatePair
      }
      STATUS  current
      DESCRIPTION
            "The eUE per Device list of objects Group."
      ::= { pktcEUEDevGroups 6}

END
